[DOCUMENT]
TITLE: MIL-STD-498: 1. Scope.
UID: 1__SCOPE_
VERSION: 1.0
DATE: 2024-12-19
CLASSIFICATION: UNCLASSIFIED

# 1. Scope.

This section shall be divided into the following paragraphs.

# 

## 1.1 Identification.

This paragraph shall contain a full identification of the system
and the software to which this document applies, including, as
applicable, identification number(s), title(s), abbreviation(s),
version number(s), and release number(s).

## 1.2 System overview.

This paragraph shall briefly state the purpose of the system and
the software to which this document applies. It shall describe the
general nature of the system and software; summarize the history of
system development, operation, and maintenance; identify the
project sponsor, acquirer, user, developer, and support agencies;
identify current and planned operating sites; and list other
relevant documents.

## 1.3 Document overview.

This paragraph shall summarize the purpose and contents of this
document and shall describe any security or privacy considerations
associated with its use.

## 1.4 Relationship to other plans.

This paragraph shall describe the relationship, if any, of the STrP
to other project management plans.

# 2. Referenced documents.

This section shall list the number, title, revision, and date of
all documents referenced in this document. This section shall also
identify the source for all documents not available through normal
Government stocking activities.

# 3. Software support resources.

This section shall be divided into paragraphs to identify and
describe the resources needed to support the deliverable software.
These resources shall include items needed to control, copy, and
distribute the software and its documentation, and to specify,
design, implement, document, test, evaluate, control, copy, and
distribute modifications to the software.

## 3.1 Facilities.

This paragraph shall describe the facilities needed to support the
deliverable software. These facilities may include special
buildings, rooms, mock-ups, building features such as raised
flooring or cabling; building features to support security and
privacy requirements (TEMPEST shielding, vaults, etc.), building
features to support safety requirements (smoke alarms, safety
glass, etc.), special power requirements, and so on. The purpose of
each item shall be described. Diagrams may be included as
applicable.

## 3.2 Hardware.

This paragraph shall identify and describe the hardware and
associated documentation needed to support the deliverable
software. This hardware may include computers, peripheral
equipment, hardware simulators, stimulators, emulators, diagnostic
equipment, and non-computer equipment. The description shall
include:

Specific models, versions, and configurations
Rationale for the selected hardware
Reference to user/operator manuals or instructions for each item,
as applicable
Identification of each hardware item and document as
acquirer-furnished, an item that will be delivered to the support
agency, an item the support agency is known to have, an item the
support agency must acquire, or other description of status
If items must be acquired, information about a current source of
supply, including whether the item is currently available and
whether it is expected to be available at the time of delivery
Information about manufacturer support, licensing, and data rights,
including whether the item is currently supported by the
manufacturer, whether it is expected to be supported at the time of
delivery, whether licenses will be assigned to the support agency,
and the terms of such licenses
Security and privacy considerations, limitations, or other items of
interest
## 3.3 Software.

This paragraph shall identify and describe the software and
associated documentation needed to support the deliverable
software. This software may include computer-aided software
engineering (CASE) tools, data in these tools, compilers, test
tools, test data, simulations, emulations, utilities, configuration
management tools, databases and data files, and other software. The
description shall include:

Specific names, identification numbers, version numbers, release
numbers, and configurations, as applicable
Rationale for the selected software
Reference to user/operator manuals or instructions for each item,
as applicable
Identification of each software item and document as
acquirer-furnished, an item that will be delivered to the support
agency, an item the support agency is known to have, an item the
support agency must acquire, or other description of status
If items must be acquired, information about a current source of
supply, including whether the item is currently available and
whether it is expected to be available at the time of delivery
Information about vendor support, licensing, and data rights,
including whether the item is currently supported by the vendor,
whether it is expected to be supported at the time of delivery,
whether licenses will be assigned to the support agency, and the
terms of such licenses
Security and privacy considerations, limitations, or other items of
interest
## 3.4 Other documentation.

This paragraph shall identify any other documentation needed to
support the deliverable software. The list will include, for
example, plans, reports, studies, specifications, design
descriptions, test cases/procedures, test reports, user/operator
manuals, and support manuals for the deliverable software. This
paragraph shall provide:

Names, identification numbers, version numbers, and release
numbers, as applicable
Rationale for including each document in the list
Identification of each document as acquirer-furnished, an item that
will be delivered to the support agency, an item the support agency
is known to have, an item the support agency must acquire, or other
description of status
If a document must be acquired, information about where to acquire
it
Information about licensing and data rights
Security and privacy considerations, limitations, or other items of
interest
## 3.5 Personnel.

This paragraph shall describe the personnel needed to support the
deliverable software, including anticipated number of personnel,
types and levels of skills and expertise, and security clearances.
This paragraph shall cite, as applicable, actual staffing on the
development project as a basis for the staffing needs cited.

## 3.6 Other resources.

This paragraph shall describe the personnel needed to support the
deliverable software, including anticipated number of personnel,
types and levels of skills and expertise, and security clearances.
This paragraph shall cite, as applicable, actual staffing on the
development project as a basis for the staffing needs cited.

## 3.6 Other resources.

This paragraph shall identify any other resources needed to support
the deliverable software. Included may be consumables such as
magnetic tapes and diskettes, together with an estimate of the type
and number that should be acquired.

## 3.7 Interrelationship of components.

This paragraph shall identify the interrelationships of the
components identified in the preceding paragraphs. A figure may be
used to show the interrelationships.

# 4. Recommended procedures.

This section shall be divided into paragraphs as needed to describe
any procedures, including advice and lessons learned, that the
developer may wish to recommend to the support agency for
supporting the deliverable software and associated support
environment.

# 5. Training.

This section shall be divided into paragraphs as appropriate to
describe the developer's plans for training support personnel to
support of the deliverable software. This section shall include:

The schedule, duration, and location for the training
The delineation between classroom training and "hands on" training
Provision (either directly or by reference) for:
1.  Familiarization with the operational software and target
    computer(s)
2.  Familiarization with the support software and host system

# 6. Anticipated areas of change.

This section shall describe anticipated areas of change to the
deliverable software.

# 7. Transition planning.

This section shall be divided into paragraphs as needed to describe
the developer's plans for transitioning the deliverable software to
the support agency. This section shall address the following:

All activities to be performed to transition the deliverable
software to the support agency. These activities may include
planning/coordination meetings; preparation of items to be
delivered to the support agency; packaging, shipment, installation,
and checkout of the software support environment; packaging,
shipment, installation, and checkout of the operational software;
and training of support personnel.
Roles and responsibilities for each activity
The resources needed to carry out the transition activities and the
source from which each resource will be provided
Schedules and milestones for conducting the transition activities.
These schedules and milestones shall be compatible with the
contract master schedule.
Procedures for installation and checkout of deliverable items in
the support environment
# 8. Notes.

This section shall contain any general information that aids in
understanding this document (e.g., background information,
glossary, rationale). This section shall include an alphabetical
listing of all acronyms, abbreviations, and their meanings as used
in this document and a list of any terms and definitions needed to
understand this document.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
