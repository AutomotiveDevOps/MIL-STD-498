[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain a full identification of the system
and the software to which this document applies, including, as
applicable, identification number(s), title(s), abbreviation(s),
version number(s), and release number(s). It shall also identify
the intended recipients of the SVD to the extent that this
identification affects the contents of the software released (for
example, source code may not be released to all recipients.)

## 1.2 System overview.

This paragraph shall briefly state the purpose of the system and
the software to which this document applies. It shall describe the
general nature of the system and software; summarize the history of
system development, operation, and maintenance; identify the
project sponsor, acquirer, user, developer, and support agencies;
identify current and planned operating sites; and list other
relevant documents.

## 1.3 Document overview.

This paragraph shall summarize the purpose and contents of this
document and shall describe any security or privacy considerations
associated with its use.

# 2. Referenced documents.

This section shall list the number, title, revision, and date of
all documents referenced in this document. This section shall also
identify the source for all documents not available through normal
Government stocking activities.

# 3. Version description.

This section shall be divided into the following paragraphs.

## 3.1 Inventory of materials released.

This paragraph shall list by identifying numbers, titles,
abbreviations, dates, version numbers, and release numbers, as
applicable, all physical media (for example, listings, tapes,
disks) and associated documentation that make up the software
version being released. It shall include applicable security and
privacy considerations for these items, safeguards for handling
them, such as concerns for static and magnetic fields, and
instructions and restrictions regarding duplication and license
provisions.

## 3.2 Inventory of software contents.

This paragraph shall list by identifying numbers, titles,
abbreviations, dates, version numbers, and release numbers, as
applicable, all computer files that make up the software version
being released. Any applicable security and privacy considerations
shall be included.

## 3.3 Changes installed.

This paragraph shall contain a list of all changes incorporated
into the software version since the previous version. If change
classes have been used, such as the Class I/Class II changes in
MIL-STD-973, the changes shall be separated into these classes.
This paragraph shall identify, as applicable, the problem reports,
change proposals, and change notices associated with each change
and the effects, if any, of each change on system operation and on
interfaces with other hardware and software. This paragraph does
not apply to the initial software version.

## 3.4 Adaptation data.

This paragraph shall identify or reference all unique to site data
contained in the software version. For software versions after the
first, this paragraph shall describe changes made to the adaptation
data.

## 3.5 Related documents.

This paragraph shall list by identifying numbers, titles,
abbreviations, dates, version numbers, and release numbers, as
applicable, all documents pertinent to the software version being
released but not included in the release.

## 3.6 Installation instructions.

This paragraph shall provide or reference the following
information, as applicable:

1.  Instructions for installing the software version
2.  Identification of other changes that have to be installed for
    this version to be used, including site-unique adaptation data not
    included in the software version
3.  Security, privacy, or safety precautions relevant to the
    installation
4.  Procedures for determining whether the version has been
    installed properly
5.  A point of contact to be consulted if there are problems or
    questions with the installation

## 3.7 Possible problems and known errors.

This paragraph shall identify any possible problems or known errors
with the software version at the time of release, any steps being
taken to resolve the problems or errors, and instructions (either
directly or by reference) for recognizing, avoiding, correcting, or
otherwise handling each one. The information presented shall be
appropriate to the intended recipient of the SVD (for example, a
user agency may need advice on avoiding errors, a support agency on
correcting them).

# 4. Notes.

This section shall contain any general information that aids in
understanding this document (e.g., background information,
glossary, rationale). This section shall include an alphabetical
listing of all acronyms, abbreviations, and their meanings as used
in this document and a list of any terms and definitions needed to
understand this document.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
