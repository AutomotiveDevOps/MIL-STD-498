[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain a full identification of the system
and the software to which this document applies, including, as
applicable, identification number(s), title(s), abbreviation(s),
version number(s), and release number(s).

## 1.2 System overview.

This paragraph shall briefly state the purpose of the system and
the software to which this document applies. It shall describe the
general nature of the system and software; summarize the history of
system development, operation, and maintenance; identify the
project sponsor, acquirer, user, developer, and support agencies;
identify current and planned operating sites; and list other
relevant documents.

## 1.3 Document overview.

This paragraph shall summarize the purpose and contents of this
plan and shall describe any security or privacy considerations
associated with its use.

## 1.4 Relationship to other plans.

This paragraph shall describe the relationship, if any, of the SIP
to other project management plans.

# 2. Referenced documents.

This section shall list the number, title, revision, and date of
all documents referenced in this plan. This section shall also
identify the source for all documents not available through normal
Government stocking activities.

# 3. Installation overview.

This section shall be divided into the following paragraphs to
provide an overview of the installation process.

## 3.1 Description.

This paragraph shall provide a general description of the
installation process to provide a frame of reference for the
remainder of the document. A list of sites for software
installation, the schedule dates, and the method of installation
shall be included.

## 3.2 Contact point.

This paragraph shall provide the organizational name, office
symbol/code, and telephone number of a point of contact for
questions relating to this installation.

## 3.3 Support materials.

This paragraph shall list the type, source, and quantity of support
materials needed for the installation. Included shall be items such
as magnetic tapes, disk packs, computer printer paper, and special
forms.

## 3.4 Training.

This paragraph shall describe the developer's plans for training
personnel who will operate and/or use the software installed at
user sites. Included shall be the delineation between general
orientation, classroom training, and "hands on" training.

## 3.5 Tasks.

This paragraph shall list and describe in general terms each task
involved in the software installation. Each task description shall
identify the organization that will accomplish the task, usually
either the user, computer operations, or the developer. The task
list shall include such items as:

1.  Providing overall planning, coordination, and preparation for
    installation
2.  Providing personnel for the installation team
3.  Arranging lodging, transportation, and office facilities for
    the installation team
4.  Ensuring that all manuals applicable to the installation are
    available when needed
5.  Ensuring that all other prerequisites have been fulfilled prior
    to the installation
6.  Planning and conducting training activities
7.  Providing students for the training
8.  Providing computer support and technical assistance for the
    installation
9.  Providing for conversion from the current system

## 3.6 Personnel.

This paragraph shall describe the number, type, and skill level of
the personnel needed during the installation period, including the
need for multishift operation, clerical support, etc.

## 3.7 Security and privacy.

This paragraph shall contain an overview of the security and
privacy considerations associated with the system.

# 4. Site-specific information for software center operations staff.

This section applies if the software will be installed in computer
center(s) or other centralized or networked software installations
for users to access via terminals or using batch inputs/outputs. If
this type of installation does not apply, this section shall
contain the words "Not applicable."

## 4.x (Site name).

This paragraph shall identify a site or set of sites and shall be
divided into the following subparagraphs to discuss those sites.
Multiple sites may be discussed together when the information for
those sites is generally the same.

### 4.x.1 Schedule.

This paragraph shall present a schedule of tasks to be accomplished
during installation. It shall depict the tasks in chronological
order with beginning and ending dates of each task and supporting
narrative as necessary.

### 4.x.2 Software inventory.

This paragraph shall provide an inventory of the software needed to
support the installation. The software shall be identified by name,
identification number, version number, release number,
configuration, and security classification, as applicable. This
paragraph shall indicate whether the software is expected to be on
site or will be delivered for the installation and shall identify
any software to be used only to facilitate the installation
process.

### 4.x.3 Facilities.

This paragraph shall detail the physical facilities and
accommodations needed during the installation period. This
description shall include the following, as applicable:

1.  Classroom, work space, and training aids needed, specifying
    hours per day, number of days, and shifts
2.  Hardware that must be operational and available
3.  Transportation and lodging for the installation team

### 4.x.4 Installation team.

This paragraph shall describe the composition of the installation
team. Each team member's tasks shall be defined.

### 4.x.5 Installation procedures.

This paragraph shall provide step-by-step procedures for
accomplishing the installation. References may be made to other
documents, such as operator manuals. Safety precautions, marked by
WARNING or CAUTION, shall be included where applicable. The
procedures shall include the following, as applicable:

1.  Installing the software
2.  Checking out the software once installed
3.  Initializing databases and other software with site-specific
    data
4.  Conversion from the current system, possibly involving running
    in parallel
5.  Dry run of the procedures in operator and user manuals

### 4.x.6 Data update procedures.

This paragraph shall present the data update procedures to be
followed during the installation period. When the data update
procedures are the same as normal updating or processing
procedures, reference may be made to other documents, such as
operator manuals.

# 5. Site-specific information for software users.

This section shall provide installation planning pertinent to users
of the software. When more than one type of user is involved, for
example, users at different positions, performing different
functions, or in different organizations, a separate section
(Sections 5 through n) may be written for each type of user and the
section titles modified to reflect each user.

## 5.x (Site name).

This paragraph shall identify a site or set of sites and shall be
divided into the following subparagraphs to discuss those sites.
Multiple sites may be discussed together when the information for
those sites is generally the same.

### 5.x.1 Schedule.

This paragraph shall present a schedule of tasks to be accomplished
by the user during installation. It shall depict the tasks in
chronological order including beginning and ending dates for each
task and supporting narrative as necessary.

### 5.x.2 Installation procedures.

This paragraph shall provide step-by-step procedures for
accomplishing the installation. Reference may be made to other
documents, such as user manuals. Safety precautions, marked by
WARNING or CAUTION, shall be included where applicable. The
procedures shall include the following, as applicable:

1.  Performing the tasks under 4.x.5 if not performed by operations
    staff
2.  Initializing user-specific data
3.  Setting up queries and other user inputs
4.  Performing sample processing
5.  Generating sample reports
6.  Conversion from the current system, possibly involving running
    in parallel
7.  Dry run of procedures in user manuals

### 5.x.3 Data update procedures.

This paragraph shall be divided into subparagraphs to present the
user's data update procedures to be followed during the
installation period. When update procedures are the same as normal
processing, reference may be made to other documents, such as user
manuals, and to Section 4 of this document

# 6. Notes.

This section shall contain any general information that aids in
understanding this document (e.g., background information,
glossary, rationale). This section shall include an alphabetical
listing of all acronyms, abbreviations, and their meanings as used
in this document and a list of terms and definitions needed to
understand this document. If section 5 has been expanded into
section(s) 6,...n, this section shall be numbered as the next
section following section n.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
