[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain the manufacturer's name, model number,
and any other identifying information for the computer system to
which this COM applies.

## 1.2 Computer system overview.

This paragraph shall briefly state the purpose of the computer
system to which this COM applies.

## 1.3 Document overview.

This paragraph shall summarize the purpose and contents of this
manual and shall describe any security or privacy considerations
associated with its use.

# 2. Referenced documents.

This section shall list the number, title, revision, and date of
all documents referenced in this manual. This section shall also
identify the source for all documents not available through normal
Government stocking activities.

# 3. Computer system operation.

This section shall be divided into the following paragraphs. Safety
precautions, marked by WARNING or CAUTION, shall be included where
applicable.

## 3.1 Computer system preparation and shutdown.

This paragraph shall be divided into the following subparagraphs.

### 3.1.1 Power on and off.

This paragraph shall contain the procedures necessary to power on
and power off the computer system.

### 3.1.2 Initiation.

This paragraph shall contain the procedures necessary to initiate
operation of the computer system, including, as applicable,
equipment setup, pre operation, bootstrapping, and commands
typically used during computer system initiation.

### 3.1.3 Shutdown.

This paragraph shall contain the procedures necessary to terminate
computer system operation.

## 3.2 Operating procedures.

This paragraph shall be divided into the following subparagraphs.
If more than one mode of operation is available, instructions for
each mode shall be provided.

### 3.2.1 Input and output procedures.

This paragraph shall describe the input and output media (e.g.,
magnetic disk, tape) relevant to the computer system, state the
procedures to read and write on these media, briefly describe the
operating system control language, and list procedures for
interactive messages and replies (e.g, terminals to use, passwords,
keys).

### 3.2.2 Monitoring procedures.

This paragraph shall contain the procedures to be followed for
monitoring the computer system in operation. It shall describe
available indicators, interpretation of those indicators, and
routine and special monitoring procedures to be followed.

### 3.2.3 Off line procedures.

This paragraph shall contain the procedures necessary to operate
all relevant off line equipment of the computer system.

### 3.2.4 Other procedures.

This paragraph shall contain any additional procedures to be
followed by the operator (e.g., computer system alarms, computer
system security or privacy considerations, switch over to a
redundant computer system, or other measures to ensure continuity
of operations in the event of emergencies).

## 3.3 Problem-handling procedures.

This paragraph shall identify problems that may occur in any step
of operation described in the preceding paragraphs in Section 3. It
shall state the error messages or other indications accompanying
those problems and shall describe the automatic and manual
procedures to be followed for each occurrence, including, as
applicable, evaluation techniques, conditions requiring computer
system shutdown, procedures for on-line intervention or abort,
steps to be taken to restart computer system operation after an
abort or interruption of operation, and procedures for recording
information concerning a malfunction.

# 4. Diagnostic features.

This section shall be divided into the following paragraphs to
describe diagnostics that may be performed to identify and
troubleshoot malfunctions in the computer system.

## 4.1 Diagnostic features summary.

This paragraph shall summarize the diagnostic features of the
computer system, including error message syntax and hierarchy for
fault isolation. This paragraph shall describe the purpose of each
diagnostic feature.

## 4.2 Diagnostic procedures.

This paragraph shall be divided into subparagraphs as needed to
describe the diagnostic proce-dures to be followed for the computer
system, including:

Identification of hardware, software, or firmware necessary for
executing each procedure
Step by step instructions for executing each procedure
Diagnostic messages and the corresponding required action
## 4.3 Diagnostic tools.

This paragraph shall be divided into subparagraphs as needed to
describe the diagnostics tools available for the computer system.
These tools may be hardware, software, or firmware. This paragraph
shall identify each tool by name and number and shall describe the
tool and its application.

# 5. Notes.

This section shall contain any general information that aids in
understanding this document (e.g., background information,
glossary, rationale). This section shall include an alphabetical
listing of all acronyms, abbreviations, and their meanings as used
in this document and a list of terms and definitions needed to
understand this document.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
