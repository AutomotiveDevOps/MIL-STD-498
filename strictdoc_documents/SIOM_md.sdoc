[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain a full identification of the system
and the software to which this document applies, including, as
applicable, identification number(s), title(s), abbreviation(s),
version number(s), and release number(s).

## 1.2 System overview.

This paragraph shall briefly state the purpose of the system and
the software to which this document applies. It shall describe the
general nature of the system and software; summarize the history of
system development, operation, and maintenance; identify the
project sponsor, acquirer, user, developer, and support agencies;
identify current and planned operating sites; and list other
relevant documents.

## 1.3 Document overview.

This paragraph shall summarize the purpose and contents of this
manual and shall describe any security or privacy considerations
associated with its use.

# 2. Referenced documents.

This section shall list the number, title, revision, and date of
all documents referenced in this manual. This section shall also
identify the source for all documents not available through normal
Government stocking activities.

# 3. Software summary.

This section shall be divided into the following paragraphs.

## 3.1 Software application.

This paragraph shall provide a brief description of the intended
uses of the software. Capabilities, operating improvements, and
benefits expected from its use shall be described.

## 3.2 Software inventory.

This paragraph shall identify the software files, if any, including
databases and data files, that the user is responsible for
requesting in order to access the software described in this
manual. The identification shall include security and privacy
considerations for each file and identification of the software
necessary to continue or resume operation in case of an emergency.

## 3.3 Software environment.

This paragraph shall identify the hardware, software, manual
operations, and other resources needed to access and use the
software. This paragraph shall be based on the assumption that the
software is installed in a computer center or other centralized or
networked environment and shall focus on the resources that a user
must have to access and use the software in that environment.
Included, as applicable, shall be identification of:

1.  Computer equipment that must be present, such as terminals,
    printers, or other input/output devices
2.  Communications equipment that must be present
3.  Other software that must be present, such as networking
    software
4.  Forms, procedures, or other manual operations that must be
    present
5.  Other facilities, equipment, or resources that must be present

## 3.4 Software organization and overview of operation.

This paragraph shall provide a brief description of the
organization and operation of the software from the user's point of
view. The description shall include, as applicable:

Logical components of the software, from the user's point of view,
including databases and data files the user can access, Database
Management Systems (DBMSs), and communications paths, and an
overview of the purpose/operation of each component
Performance characteristics that can be expected by the user, such
as:
1.  Types, volumes, rate of inputs accepted
2.  Types, volume, accuracy, rate of outputs that the software can
    produce
3.  Typical response time and factors that affect it
4.  Typical processing time and factors that affect it
5.  Limitations, e.g, restrictions on what data may be queried and
    from what location
6.  Error rate that can be expected
7.  Reliability that can be expected

Relationships of the functions performed by the software with
interfacing systems and with the organizations or stations that are
sources of input or recipients of output
Supervisory controls that can be implemented (such as passwords) to
manage the software
## 3.5 Contingencies and alternate states and modes of operation.

This paragraph shall explain the differences in what the user will
be able to do with the software at times of emergency and in
various states and modes of operation, if applicable.

## 3.6 Security and privacy.

This paragraph shall contain an overview of the security and
privacy considerations associated with the software. A warning
shall be included regarding making unauthorized copies of software
or documents, if applicable.

## 3.7 Assistance and problem reporting.

This paragraph shall identify points of contact and procedures to
be followed to obtain assistance and report problems encountered in
using the software.

# 4. Using the software.

This section shall be divided into the following paragraphs to
describe how to prepare inputs to, and interpret output from, the
software. If the software has a query capability, this paragraph
shall reference section 5 for a description of this capability. If
the software can be accessed via terminal, this paragraph shall
reference Sections 6 through n to describe terminal processing
procedures. Safety precautions, marked by WARNING or CAUTION, shall
be included where applicable.

## 4.1 Initiation procedures.

This paragraph shall contain the procedures that must be followed
to initiate use of the software. Included may be information such
as sample job request forms or sample control statements.

## 4.2 Description of inputs.

This paragraph shall be divided into the following subparagraphs.

### 4.2.1 Input conditions.

This paragraph shall describe the conditions to be observed in
preparing each type or class of input to the software. The
conditions shall include the following, as applicable:

1.  Reason for input, such as normal status report, need to update
    data
2.  Frequency of input, such as monthly, on demand
3.  Origin of input, such as the organization or station authorized
    to generate the input
4.  Medium of input, such as magnetic tape
5.  Related inputs that are required to be entered at the same time
    as this input
6.  Other applicable information, such as priority; security and
    privacy considerations

### 4.2.2 Input formats.

This paragraph shall illustrate the layout formats to be used in
the preparation of inputs to the software and shall explain the
information that may be entered in the various sections and lines
of each format.

### 4.2.3 Composition rules.

This paragraph shall describe any rules and conventions that must
be observed to prepare inputs. The rules of syntax, usage of
punctuation, etc., shall be explained. The rules shall include the
following, as applicable:

1.  Input transaction length, such as 100 characters maximum
2.  Format conventions, such as all input items must be
    left-justified
3.  Labeling, such as usage of identifiers to denote major data
    sets to the software
4.  Sequencing, such as order and placement of items in the input
5.  Punctuation, such as spacing and use of symbols (virgule,
    asterisk, character combina-tions, etc.) to denote start and end of
    input, of data groups, and of fields
6.  Restrictions, such as rules forbidding use of particular
    characters or parameter sets

### 4.2.4 Input vocabulary.

This paragraph shall explain the legal character combinations or
codes that must be used to prepare inputs. An appendix may be
provided containing an ordered listing of these codes.

### 4.2.5 Sample inputs.

This paragraph shall provide examples that illustrate and explain
each type or class of input acceptable by the software. Included
shall be information on the following types of inputs, as
applicable:

1.  Headers denoting the start of input
2.  Text or body of the input
3.  Trailers denoting the end of input
4.  Portions of the input that may be omitted
5.  Portions of the input that may be repeated

## 4.3 Description of outputs.

This paragraph shall be divided into the following subparagraphs.

### 4.3.1 General description.

This paragraph shall provide the following information, as
applicable, for each type or class of output:

1.  Reasons why the output is generated
2.  Frequency of the output, such as monthly, on demand
3.  Any modifications or variations of the basic output that are
    available
4.  Media, such as printout, display screen, tape
5.  Location where the output will appear, such as in the computer
    area or remotely
6.  Any additional characteristics, such as priority, security and
    privacy considerations, associated outputs that complement the
    information in this output

### 4.3.2 Output formats.

This paragraph shall illustrate and explain the layout of each type
or class of output from the software. The following aspects shall
be explained, as applicable:

1.  Security and privacy markings
2.  Data that may appear in headers
3.  Information that may appear in the body or text of the output,
    including column headings and subsets or sections in the output
    format
4.  Data that may appear in trailers
5.  Additional characteristics, such as the meaning of special
    symbols

### 4.3.3 Sample outputs.

This paragraph shall provide illustrations of each type or class of
output from the software. A description of each sample shall be
provided, including, as applicable:

1.  Meaning and use of each column, entry, etc.
2.  Source, such as extracted from database, calculated
3.  Characteristics, such as when omitted, range of values, unit of
    measure

### 4.3.4 Output vocabulary.

This paragraph shall describe any codes or abbreviations that
appear in the output that differ from those used in the input
described in paragraph 4.2.4.

## 4.4 Use of outputs.

This paragraph shall explain the use of the output by the
operational area or activity that receives it.

## 4.5 Recovery and error correction procedures.

This paragraph shall list the error codes generated by the
software, give their meanings, and describe the corrective actions
to be taken by the user. Also included shall be the procedures to
be followed by the user with respect to restart, recovery, and
continuity of operations in the event of emergencies.

## 4.6 Communications diagnostics.

This paragraph shall describe the diagnostic procedures available
to the user for validating communications and for identifying and
classifying problems.

# 5. Query procedures.

This section shall be prepared for software with a query
capability. It shall be divided into the following paragraphs.

## 5.1 Database/data file format.

This paragraph shall provide a user's view of the format and
content of each database and data file that can be queried. Figure
1 provides an example. Information such as the following shall be
provided for each data element, as applicable:

1.  Data element name
2.  Synonymous names
3.  Definition
4.  Format
5.  Range and enumeration of values
6.  Unit of measurement
7.  Data item names, abbreviations, and codes

## 5.2 Query capabilities.

This paragraph shall identify and describe the preprogrammed and ad
hoc query capabilities provided by the software. An example of
preprogrammed queries is shown in Figure 2.

## 5.3 Query preparation.

This paragraph shall provide instructions for preparing queries.
Figure 3 shows an example of the format for a preprogrammed query.
Figure 4 shows an example of a query statement.

## 5.4 Control instructions.

This paragraph shall provide instructions for the sequencing of
runs and other actions necessary to extract responses to query
requests. These instructions shall include control statements that
may be required by the computer system or software.

# 6. User terminal processing procedures.

This section shall be divided into the following paragraphs to
provide the user with information on the use of terminals to
accomplish processing. If the procedures are complicated or
extensive, Sections 7 through n may be added in the same paragraph
structure as this section and with titles meaningful to the
sections selected. The organization of the document will depend on
the characteristics of the software being documented. For example,
sections might be based on the organizations in which users work,
their assigned positions, work sites, or the tasks they must
perform. For other software, it may be more appropriate to have
Section 6 be a guide to menus, Section 7 be a guide to the command
language, and Section 8 be a guide to functions. Detailed
procedures are intended to be presented in paragraphs 6.2 through
6.5. Depending on the design of the software, the subparagraphs
might be organized on a function by function, menu by menu,
transaction-by-transaction, or other basis. Safety precautions,
marked by WARNING or CAUTION, shall be included where applicable.

## 6.1 Available capabilities.

This paragraph shall describe in general terms the capabilities for
retrieval, display, and update of data through terminal
operations.

## 6.2 Access procedures.

This paragraph shall present the sequence of steps and any
applicable rules pertaining to accessing the software to initiate
software operations.

## 6.3 Display, updates, and retrieval procedures.

This paragraph shall be divided into subparagraphs to provide the
step-by-step procedures necessary to produce the displays, updates,
and retrievals that are available through the use of a terminal.
Each procedure shall include the name of the operation, input
formats, and sample responses, as applicable.

## 6.4 Recovery and error correction procedures.

This paragraph shall identify error messages that may be displayed
and shall indicate their meanings and any corrective actions that
should be taken. Also included shall be any procedures to be
followed by the user with respect to restart, recovery, and
continuity of operations in the event of emergencies.

## 6.5 Termination procedures.

This paragraph shall present the sequence of steps necessary to
terminate the processing.

# 7. Notes.

This section shall contain any general information that aids in
understanding this document (e.g., background information,
glossary, rationale). This section shall include an alphabetical
listing of all acronyms, abbreviations, and their meanings as used
in this document and a list of terms and definitions needed to
understand this document. If section 6 has been expanded into
section(s) 7,..., this section shall be numbered as the next
section following section n.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
