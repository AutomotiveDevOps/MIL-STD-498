[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain the manufacturer's name, model number,
and any other identifying information for the computer system to
which this document applies.

## 1.2 Computer system overview.

This paragraph shall briefly state the purpose of the computer
system to which this document applies.

## 1.3 Document overview.

This paragraph shall summarize the purpose and contents of this
manual and shall describe any security or privacy considerations
associated with its use.

# 2. Referenced documents.

This section shall list the number, title, revision, and date of
all documents referenced in this manual. This section shall also
identify the source for all documents not available through normal
Government stocking activities.

# 3. Programming environment.

This section shall be divided into paragraphs as appropriate to
provide the following information.

The components and configuration of the computer system
Operating characteristics, capabilities, and limitations,
including, as applicable:
1.  Machine cycle time
2.  Word length
3.  Memory capacity and characteristics
4.  Instruction set characteristics
5.  Interrupt capabilities
6.  Modes of operation (e.g., batch, interactive, privileged,
    non-privileged)
7.  Operational registers
8.  Error indicators Input/output characteristics
9.  Input/output characteristics
10. Special features

Description of the equipment (e.g., tapes, disks, other peripheral
equipment) necessary to perform compilations and assemblies on the
computer system. Identify (as applicable) by name and version
number the editor, linker, link editor, compiler, assembler, cross
compilers, cross assemblers, and other utilities used, and
reference appropriate manuals describing their use. Highlight any
special flags or instructions necessary for loading, executing, or
recording the results.
# 4. Programming information.

This section shall be divided into paragraphs as appropriate to
provide the following information.

Description of the programming features of the computer's
instruction set architecture, including, as applicable:
1.  Data representation (e.g., byte, word, integer, floating point,
    double precision)
2.  Instruction formats and addressing modes
3.  Special registers and words (e.g., stack pointer, program
    counter)
4.  Control instructions (e.g., branch, jump, subroutine and
    procedure call instructions, privileged instructions, and the modes
    they operate in)
5.  Subroutines and procedures (e.g., non reentrant, reentrant,
    macrocode routines, argument lists, parameter passing conventions)
6.  Interrupt processing
7.  Timers and clocks
8.  Memory protection features (e.g., read only memory)
9.  Additional features, such as instruction or data cache
    architecture

Description of each instruction, including, as applicable:
1.  Use
2.  Syntax
3.  Condition codes set
4.  Execution time
5.  Machine code format
6.  Mnemonic conventions
7.  Other characteristics

Description of input and output control programming, including, as
applicable:
1.  Initial loading and verification of computer memory
2.  Serial and parallel data channels
3.  Discrete inputs and outputs
4.  Interface components
5.  Device numbers, operational codes, and memory locations for
    peripheral equipment

Additional, restricted, or special programming techniques
associated with the computer system (e.g., a concise description of
the microprogram control section)
Examples that demonstrate the programming features described above,
including examples of the proper use of all categories of
instructions on the computer system
Error detection and diagnostic features associated with the
computer system, including condition codes, overflow and addressing
exception interrupts, and input and output error status indicators
# 5. Notes.

This section shall contain any general information that aids in
understanding this document (e.g., background information,
glossary, rationale). This section shall include an alphabetical
listing of all acronyms, abbreviations, and their meanings as used
in this document and a list of terms and definitions needed to
understand this document

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
