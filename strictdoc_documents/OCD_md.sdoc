[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain a full identification of the system to
which this document applies, including, as applicable,
identification number(s), title(s), abbreviation(s), version
number(s), and release number(s).

## 1.2 System overview.

This paragraph shall briefly state the purpose of the system to
which this document applies. It shall describe the general nature
of the system; summarize the history of system development,
operation, and maintenance; identify the project sponsor, acquirer,
user, developer, and support agencies; identify current and planned
operating sites; and list other relevant documents.

## 1.3 Document overview.

This paragraph shall summarize the purpose and contents of this
document and shall describe any security or privacy considerations
associated with its use.

# 2. Referenced documents.

This section shall list the number, title, revision, and date of
all documents referenced in this document. This section shall also
identify the source for all documents not available through normal
Government stocking activities.

# 3. Current system or situation.

This section shall be divided into the following paragraphs to
describe the system or situation as it currently exists.

## 3.1 Background, objectives, and scope.

This paragraph shall describe the background, mission or
objectives, and scope of the current system or situation.

## 3.2 Operational policies and constraints.

This paragraph shall describe any operational policies and
constraints that apply to the current system or situation.

## 3.3 Description of current system or situation.

This paragraph shall provide a description of the current system or
situation, identifying differences associated with different states
or modes of operation (for example, regular, mainte-nance,
training, degraded, emergency, alternative-site, wartime,
peacetime). The distinction between states and modes is arbitrary.
A system may be described in terms of states only, modes only,
states within modes, modes within states, or any other scheme that
is useful. If the system operates without states or modes, this
paragraph shall so state, without the need to create artificial
distinctions. The description shall include, as applicable:

The operational environment and its characteristics
Major system components and the interconnections among these
components
Interfaces to external systems or procedures
Capabilities/functions of the current system
Charts and accompanying descriptions depicting inputs, outputs,
data flow, and manual and automated processes sufficient to
understand the current system or situation from the user's point of
view
Performance characteristics, such as speed, throughput, volume,
frequency
Quality attributes, such as reliability, maintainability,
availability, flexibility, portability, usability, efficiency
Provisions for safety, security, privacy, and continuity of
operations in emergencies
## 3.4 Users or involved personnel.

This paragraph shall describe the types of users of the system, or
personnel involved in the current situation, including, as
applicable, organizational structures, training/skills,
responsibilities, activities, and interactions with one another.

## 3.5 Support concept.

This paragraph shall provide an overview of the support concept for
the current system, including, as applicable to this document,
support agency(ies); facilities; equipment; support software;
repair/replacement criteria; maintenance levels and cycles; and
storage, distribution, and supply methods.

# 4. Justification for and nature of changes.

This section shall be divided into the following paragraphs.

## 4.1 Justification for change.

This paragraph shall:

Describe new or modified aspects of user needs, threats, missions,
objectives, environ-ments, interfaces, personnel or other factors
that require a new or modified system
Summarize deficiencies or limitations in the current system or
situation that make it unable to respond to these factors
## 4.2 Description of needed changes.

This paragraph shall summarize new or modified
capabilities/functions, processes, interfaces, or other changes
needed to respond to the factors identified in 4.1.

## 4.3 Priorities among the changes.

This paragraph shall identify priorities among the needed changes.
It shall, for example, identify each change as essential,
desirable, or optional, and prioritize the desirable and optional
changes.

## 4.4 Changes considered but not included.

This paragraph shall identify changes considered but not included
in 4.2, and rationale for not including them.

## 4.5 Assumptions and constraints.

This paragraph shall identify any assumptions and constraints
applicable to the changes identi-fied in this section.

# 5. Concept for a new or modified system.

This section shall be divided into the following paragraphs to
describe a new or modified system.

## 5.1 Background, objectives, and scope.

This paragraph shall describe the background, mission or
objectives, and scope of the new or modified system.

## 5.2 Operational policies and constraints.

This paragraph shall describe any operational policies and
constraints that apply to the new or modified system.

## 5.3 Description of the new or modified system.

This paragraph shall provide a description of the new or modified
system, identifying differences associated with different states or
modes of operation (for example, regular, maintenance, train-ing,
degraded, emergency, alternative-site, wartime, peacetime). The
distinction between states and modes is arbitrary. A system may be
described in terms of states only, modes only, states within modes,
modes within states, or any other scheme that is useful. If the
system operates without states or modes, this paragraph shall so
state, without the need to create artificial distinctions. The
description shall include, as applicable:

The operational environment and its characteristics
Major system components and the interconnections among these
components
Interfaces to external systems or procedures
Capabilities/functions of the new or modified system
Charts and accompanying descriptions depicting inputs, outputs,
data flow, and manual and automated processes sufficient to
understand the new or modified system or situation from the user's
point of view
Performance characteristics, such as speed, throughput, volume,
frequency
Quality attributes, such as reliability, maintainability,
availability, flexibility, portability, usability, efficiency
Provisions for safety, security, privacy, and continuity of
operations in emergencies
## 5.4 Users/affected personnel.

This paragraph shall describe the types of users of the new or
modified system, including, as applicable, organizational
structures, training/skills, responsibilities, and interactions
with one another.

## 5.5 Support concept.

This paragraph shall provide an overview of the support concept for
the new or modified system, including, as applicable, support
agency(ies); facilities; equipment; support software;
repair/replacement criteria; maintenance levels and cycles; and
storage, distribution, and supply methods.

# 6. Operational scenarios.

This section shall describe one or more operational scenarios that
illustrate the role of the new or modified system, its interaction
with users, its interface to other systems, and all states or modes
identified for the system. The scenarios shall include events,
actions, stimuli, information, interactions, etc., as applicable.
Reference may be made to other media, such as videos, to provide
part or all of this information.

# 7. Summary of impacts.

This section shall be divided into the following paragraphs.

## 7.1 Operational impacts.

This paragraph shall describe anticipated operational impacts on
the user, acquirer, developer, and support agency(ies). These
impacts may include changes in interfaces with computer operating
centers; change in procedures; use of new data sources; changes in
quantity, type, and timing of data to be input to the system;
changes in data retention requirements; and new modes of operation
based on peacetime, alert, wartime, or emergency conditions.

## 7.2 Organizational impacts.

This paragraph shall describe anticipated organizational impacts on
the user, acquirer, developer, and support agency(ies). These
impacts may include modification of responsibilities; addition or
elimination of responsibilities or positions; need for training or
retraining; and changes in number, skill levels, position
identifiers, or location of personnel in various modes of
operation.

## 7.3 Impacts during development.

This paragraph shall describe anticipated impacts on the user,
acquirer, developer, and support agency(ies) during the development
effort. These impacts may include meetings/discussions regarding
the new system; development or modification of databases; training;
parallel operation of the new and existing systems; impacts during
testing of the new system; and other activities needed to aid or
monitor development.

# 8. Analysis of the proposed system.

## 8.1 Summary of advantages.

This paragraph shall provide a qualitative and quantitative summary
of the advantages to be obtained from the new or modified system.
This summary shall include new capabilities, enhanced capabilities,
and improved performance, as applicable, and their relationship to
deficiencies identified in 4.1.

## 8.2 Summary of disadvantages/limitations.

This paragraph shall provide a qualitative and quantitative summary
of disadvantages or limitations of the new or modified system.
These disadvantages and limitations shall include, as applicable,
degraded or missing capabilities, degraded or less-than-desired
performance, greater-than-desired use of computer hardware
resources, undesirable operational impacts, conflicts with user
assumptions, and other constraints.

## 8.3 Alternatives and trade-offs considered.

This paragraph shall identify and describe major alternatives
considered to the system or its characteristics, the trade-offs
among them, and rationale for the decisions reached.

# 9. Notes.

This section shall contain any general information that aids in
understanding this document (e.g., background information,
glossary, rationale). This section shall include an alphabetical
listing of all acronyms, abbreviations, and their meanings as used
in this document and a list of any terms and definitions needed to
understand this document.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
