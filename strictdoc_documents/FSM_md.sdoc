[DOCUMENT]
TITLE: MIL-STD-498: 1. Scope.
UID: 1__SCOPE_
VERSION: 1.0
DATE: 2024-12-19
CLASSIFICATION: UNCLASSIFIED

# 1. Scope.

This section shall be divided into the following paragraphs.

## 1.1 Identification.

This paragraph shall contain a full identification of the system,
software, and firmware devices to which this document applies,
including, as applicable, identification number(s), title(s),
abbreviation(s), version number(s), and release number(s) of the
system and software and manufacturer's name and model number for
each firmware device.

## 1.2 System overview.

This paragraph shall briefly state the purpose of the system and
the software to which this document applies. It shall describe the
general nature of the system and software; summarize the history of
system development, operation, and maintenance; identify the
project sponsor, acquirer, user, developer, and support agencies;
identify current and planned operating sites; and list other
relevant documents.

## 1.3 Document overview.

This paragraph shall summarize the purpose and contents of this
manual and shall describe any security or privacy considerations
associated with its use.

# 2. Referenced documents.

This section shall list the number, title, revision, and date of
all documents referenced in this manual. This section shall also
identify the source for all documents not available through normal
Government stocking activities.

# 3. Firmware programming instructions.

This section shall be divided into the following paragraphs.

## 3.x (Identifier of programmed firmware device).

This paragraph shall state the project-unique identifier of a
programmed firmware device to be used in the system and shall be
divided into the following subparagraphs.

### 3.x.1 Description of pre-programmed device.

This paragraph shall:

Identify by manufacturer's name and model number the firmware
device to be programmed
Provide a complete physical description of the firmware device,
including the following, as applicable:
1.  Memory size, type, speed, and configuration (such as 64Kx1,
    8Kx8)
2.  Operating characteristics (such as access time, power
    requirements,logic levels)
3.  Pin functional descriptions
4.  Logical interfaces (such as addressing scheme, chip selection)
5.  Internal and external identification scheme used
6.  Timing diagrams

Describe the operational and environmental limits to which the
firmware device may be subjected and still maintain satisfactory
operation
### 3.x.2 Software to be programmed into the device.

This paragraph shall identify by project-unique identifier(s) the
software to be programmed into the firmware device.

### 3.x.3 Programming equipment.

This paragraph shall describe the equipment to be used for
programming and reprogramming the firmware device. It shall include
computer equipment, general purpose equipment, and special
equipment to be used for device erasure, loading, verification, and
marking, as applicable. Each piece of equipment shall be identified
by manufacturer's name, model number, and any other information
that is necessary to uniquely identify that piece of equipment. A
description of each piece of equipment shall be provided, including
its purpose, usage, and major capabilities.

### 3.x.4 Programming software.

This paragraph shall describe the software to be used for
programming and reprogramming the firmware device. It shall include
software to be used for device erasure, loading, verification, and
marking, as applicable. Each software item shall be identified by
vendor's name, software name, number, version/release, and any
other information necessary to uniquely identify the software item.
A description of each software item shall be provided, including
its purpose, usage, and major capabilities.

### 3.x.5 Programming procedures.

This paragraph shall describe the procedures to be used for
programming and reprogramming the firmware device. It shall include
procedures to be used for device erasure, loading, verification,
and marking, as applicable. All equipment and software necessary
for each procedure shall be identified, together with any security
and privacy measures to be applied.

### 3.x.6 Installation and repair procedures.

This paragraph shall contain the installation, replacement, and
repair procedures for the firmware device. This paragraph shall
also include remove and replace procedures, device addressing
scheme and implementation, description of the host board layout,
and any procedures for ensuring continuity of operations in the
event of emergencies. Safety precautions, marked by WARNING or
CAUTION, shall be included where applicable.

### 3.x.7 Vendor information.

This section shall include or reference any relevant information
supplied by the vendor(s) of the firmware device, programming
equipment, or programming software.

# 4. Notes.

This section shall contain any general information that aids in
understanding this document (e.g., background information,
glossary, rationale). This section shall include an alphabetical
listing of all acronyms, abbreviations, and their meanings as used
in this document and a list of terms and definitions needed to
understand this document.

# A. Appendixes.

Appendixes may be used to provide information published separately
for convenience in document maintenance (e.g., charts, classified
data). As applicable, each appendix shall be referenced in the main
body of the document where the data would normally have been
provided. Appendixes may be bound as separate documents for ease in
handling. Appendixes shall be lettered alphabetically (A, B,
etc.).
