[DOCUMENT]
TITLE: FSM.html

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-516
STATUS: Draft
TITLE: 1. Scope.
STATEMENT: This section shall be divided into the following paragraphs.
RATIONALE: Converted from FSM.html.md heading.

[REQUIREMENT]
UID: REQ-517
STATUS: Draft
TITLE: 1.1 Identification.
STATEMENT: This paragraph shall contain a full identification of the system, software, and firmware devices to which this document applies, including, as applicable, identification number(s), title(s), abbreviation(s), version number(s), and release number(s) of the system and software and manufacturer's name and model number for each firmware device.
RATIONALE: Converted from FSM.html.md heading.

[REQUIREMENT]
UID: REQ-518
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from FSM.html.md heading.

[REQUIREMENT]
UID: REQ-519
STATUS: Draft
TITLE: 1.3 Document overview.
STATEMENT: This paragraph shall summarize the purpose and contents of this manual and shall describe any security or privacy considerations associated with its use.
RATIONALE: Converted from FSM.html.md heading.

[REQUIREMENT]
UID: REQ-520
STATUS: Draft
TITLE: 2. Referenced documents.
STATEMENT: This section shall list the number, title, revision, and date of all documents referenced in this manual. This section shall also identify the source for all documents not available through normal Government stocking activities.
RATIONALE: Converted from FSM.html.md heading.

[REQUIREMENT]
UID: REQ-521
STATUS: Draft
TITLE: 3. Firmware programming instructions.
STATEMENT: This section shall be divided into the following paragraphs.
RATIONALE: Converted from FSM.html.md heading.

[REQUIREMENT]
UID: REQ-522
STATUS: Draft
TITLE: 3.x (Identifier of programmed firmware device).
STATEMENT: This paragraph shall state the projectunique identifier of a programmed firmware device to be used in the system and shall be divided into the following subparagraphs.
RATIONALE: Converted from FSM.html.md heading.

[REQUIREMENT]
UID: REQ-523
STATUS: Draft
TITLE: 3.x.1 Description of preprogrammed device.
STATEMENT: This paragraph shall: Identify by manufacturer's name and model number the firmware device to be programmed Provide a complete physical description of the firmware device, including the following, as applicable: 1. Memory size, type, speed, and configuration (such as 64Kx1, 8Kx8) 2. Operating characteristics (such as access time, power requirements,logic levels) 3. Pin functional descriptions 4. Logical interfaces (such as addressing scheme, chip selection) 5. Internal and external identifica...
RATIONALE: Converted from FSM.html.md heading.

[REQUIREMENT]
UID: REQ-524
STATUS: Draft
TITLE: 3.x.2 Software to be programmed into the device.
STATEMENT: This paragraph shall identify by projectunique identifier(s) the software to be programmed into the firmware device.
RATIONALE: Converted from FSM.html.md heading.

[REQUIREMENT]
UID: REQ-525
STATUS: Draft
TITLE: 3.x.3 Programming equipment.
STATEMENT: This paragraph shall describe the equipment to be used for programming and reprogramming the firmware device. It shall include computer equipment, general purpose equipment, and special equipment to be used for device erasure, loading, verification, and marking, as applicable. Each piece of equipment shall be identified by manufacturer's name, model number, and any other information that is necessary to uniquely identify that piece of equipment. A description of each piece of equipment shall ...
RATIONALE: Converted from FSM.html.md heading.

[REQUIREMENT]
UID: REQ-526
STATUS: Draft
TITLE: 3.x.4 Programming software.
STATEMENT: This paragraph shall describe the software to be used for programming and reprogramming the firmware device. It shall include software to be used for device erasure, loading, verification, and marking, as applicable. Each software item shall be identified by vendor's name, software name, number, version/release, and any other information necessary to uniquely identify the software item. A description of each software item shall be provided, including its purpose, usage, and major capabilities.
RATIONALE: Converted from FSM.html.md heading.

[REQUIREMENT]
UID: REQ-527
STATUS: Draft
TITLE: 3.x.5 Programming procedures.
STATEMENT: This paragraph shall describe the procedures to be used for programming and reprogramming the firmware device. It shall include procedures to be used for device erasure, loading, verification, and marking, as applicable. All equipment and software necessary for each procedure shall be identified, together with any security and privacy measures to be applied.
RATIONALE: Converted from FSM.html.md heading.

[REQUIREMENT]
UID: REQ-528
STATUS: Draft
TITLE: 3.x.6 Installation and repair procedures.
STATEMENT: This paragraph shall contain the installation, replacement, and repair procedures for the firmware device. This paragraph shall also include remove and replace procedures, device addressing scheme and implementation, description of the host board layout, and any procedures for ensuring continuity of operations in the event of emergencies. Safety precautions, marked by WARNING or CAUTION, shall be included where applicable.
RATIONALE: Converted from FSM.html.md heading.

[REQUIREMENT]
UID: REQ-529
STATUS: Draft
TITLE: 3.x.7 Vendor information.
STATEMENT: This section shall include or reference any relevant information supplied by the vendor(s) of the firmware device, programming equipment, or programming software.
RATIONALE: Converted from FSM.html.md heading.

[REQUIREMENT]
UID: REQ-530
STATUS: Draft
TITLE: 4. Notes.
STATEMENT: This section shall contain any general information that aids in understanding this document (e.g., background information, glossary, rationale). This section shall include an alphabetical listing of all acronyms, abbreviations, and their meanings as used in this document and a list of terms and definitions needed to understand this document.
RATIONALE: Converted from FSM.html.md heading.

[REQUIREMENT]
UID: REQ-531
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from FSM.html.md heading.
