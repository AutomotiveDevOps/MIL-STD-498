[DOCUMENT]
TITLE: SVD.html

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-532
STATUS: Draft
TITLE: 1. Scope.
STATEMENT: This section shall be divided into the following paragraphs.
RATIONALE: Converted from SVD.html.md heading.

[REQUIREMENT]
UID: REQ-533
STATUS: Draft
TITLE: 1.1 Identification.
STATEMENT: This paragraph shall contain a full identification of the system and the software to which this document applies, including, as applicable, identification number(s), title(s), abbreviation(s), version number(s), and release number(s). It shall also identify the intended recipients of the SVD to the extent that this identification affects the contents of the software released (for example, source code may not be released to all recipients.)
RATIONALE: Converted from SVD.html.md heading.

[REQUIREMENT]
UID: REQ-534
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from SVD.html.md heading.

[REQUIREMENT]
UID: REQ-535
STATUS: Draft
TITLE: 1.3 Document overview.
STATEMENT: This paragraph shall summarize the purpose and contents of this document and shall describe any security or privacy considerations associated with its use.
RATIONALE: Converted from SVD.html.md heading.

[REQUIREMENT]
UID: REQ-536
STATUS: Draft
TITLE: 2. Referenced documents.
STATEMENT: This section shall list the number, title, revision, and date of all documents referenced in this document. This section shall also identify the source for all documents not available through normal Government stocking activities.
RATIONALE: Converted from SVD.html.md heading.

[REQUIREMENT]
UID: REQ-537
STATUS: Draft
TITLE: 3. Version description.
STATEMENT: This section shall be divided into the following paragraphs.
RATIONALE: Converted from SVD.html.md heading.

[REQUIREMENT]
UID: REQ-538
STATUS: Draft
TITLE: 3.1 Inventory of materials released.
STATEMENT: This paragraph shall list by identifying numbers, titles, abbreviations, dates, version numbers, and release numbers, as applicable, all physical media (for example, listings, tapes, disks) and associated documentation that make up the software version being released. It shall include applicable security and privacy considerations for these items, safeguards for handling them, such as concerns for static and magnetic fields, and instructions and restrictions regarding duplication and license ...
RATIONALE: Converted from SVD.html.md heading.

[REQUIREMENT]
UID: REQ-539
STATUS: Draft
TITLE: 3.2 Inventory of software contents.
STATEMENT: This paragraph shall list by identifying numbers, titles, abbreviations, dates, version numbers, and release numbers, as applicable, all computer files that make up the software version being released. Any applicable security and privacy considerations shall be included.
RATIONALE: Converted from SVD.html.md heading.

[REQUIREMENT]
UID: REQ-540
STATUS: Draft
TITLE: 3.3 Changes installed.
STATEMENT: This paragraph shall contain a list of all changes incorporated into the software version since the previous version. If change classes have been used, such as the Class I/Class II changes in MILSTD973, the changes shall be separated into these classes. This paragraph shall identify, as applicable, the problem reports, change proposals, and change notices associated with each change and the effects, if any, of each change on system operation and on interfaces with other hardware and software....
RATIONALE: Converted from SVD.html.md heading.

[REQUIREMENT]
UID: REQ-541
STATUS: Draft
TITLE: 3.4 Adaptation data.
STATEMENT: This paragraph shall identify or reference all unique to site data contained in the software version. For software versions after the first, this paragraph shall describe changes made to the adaptation data.
RATIONALE: Converted from SVD.html.md heading.

[REQUIREMENT]
UID: REQ-542
STATUS: Draft
TITLE: 3.5 Related documents.
STATEMENT: This paragraph shall list by identifying numbers, titles, abbreviations, dates, version numbers, and release numbers, as applicable, all documents pertinent to the software version being released but not included in the release.
RATIONALE: Converted from SVD.html.md heading.

[REQUIREMENT]
UID: REQ-543
STATUS: Draft
TITLE: 3.6 Installation instructions.
STATEMENT: This paragraph shall provide or reference the following information, as applicable: 1. Instructions for installing the software version 2. Identification of other changes that have to be installed for this version to be used, including siteunique adaptation data not included in the software version 3. Security, privacy, or safety precautions relevant to the installation 4. Procedures for determining whether the version has been installed properly 5. A point of contact to be consulted if there...
RATIONALE: Converted from SVD.html.md heading.

[REQUIREMENT]
UID: REQ-544
STATUS: Draft
TITLE: 3.7 Possible problems and known errors.
STATEMENT: This paragraph shall identify any possible problems or known errors with the software version at the time of release, any steps being taken to resolve the problems or errors, and instructions (either directly or by reference) for recognizing, avoiding, correcting, or otherwise handling each one. The information presented shall be appropriate to the intended recipient of the SVD (for example, a user agency may need advice on avoiding errors, a support agency on correcting them).
RATIONALE: Converted from SVD.html.md heading.

[REQUIREMENT]
UID: REQ-545
STATUS: Draft
TITLE: 4. Notes.
STATEMENT: This section shall contain any general information that aids in understanding this document (e.g., background information, glossary, rationale). This section shall include an alphabetical listing of all acronyms, abbreviations, and their meanings as used in this document and a list of any terms and definitions needed to understand this document.
RATIONALE: Converted from SVD.html.md heading.

[REQUIREMENT]
UID: REQ-546
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SVD.html.md heading.
