[DOCUMENT]
TITLE: IDD.html

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-364
STATUS: Draft
TITLE: 1. Scope.
STATEMENT: This section shall be divided into the following paragraphs.
RATIONALE: Converted from IDD.html.md heading.

[REQUIREMENT]
UID: REQ-365
STATUS: Draft
TITLE: 1.1 Identification.
STATEMENT: This paragraph shall contain a full identification of the system(s), the interfacing entities, and interfaces to which this document applies, including, as applicable, identification number(s), title(s), abbreviation(s), version number(s), and release number(s).
RATIONALE: Converted from IDD.html.md heading.

[REQUIREMENT]
UID: REQ-366
STATUS: Draft
TITLE: 1.2 System overview.
STATEMENT: This paragraph shall briefly state the purpose of the system(s) and software to which this document applies. It shall describe the general nature of the system and software; summarize the history of system development, operation, and maintenance; identify the project sponsor, acquirer, user, developer, and support agencies; identify current and planned operating sites; and list other relevant documents.
RATIONALE: Converted from IDD.html.md heading.

[REQUIREMENT]
UID: REQ-367
STATUS: Draft
TITLE: 1.3 Document overview.
STATEMENT: This paragraph shall summarize the purpose and contents of this document and shall describe any security or privacy considerations associated with its use.
RATIONALE: Converted from IDD.html.md heading.

[REQUIREMENT]
UID: REQ-368
STATUS: Draft
TITLE: 2. Referenced documents.
STATEMENT: This section shall list the number, title, revision, and date of all documents referenced in this document. This section shall also identify the source for all documents not available through normal Government stocking activities.
RATIONALE: Converted from IDD.html.md heading.

[REQUIREMENT]
UID: REQ-369
STATUS: Draft
TITLE: 3. Interface design.
STATEMENT: This section shall be divided into the following paragraphs to describe the interface characteristics of one or more systems, subsystems, configuration items, manual operations, or other system components. If part or all of the design depends upon system states or modes, this dependency shall be indicated. If design information falls into more than one paragraph, it may be presented once and referenced from the other paragraphs. If part or all of this information is documented elsewhere, it m...
RATIONALE: Converted from IDD.html.md heading.

[REQUIREMENT]
UID: REQ-370
STATUS: Draft
TITLE: 3.1 Interface identification and diagrams.
STATEMENT: For each interface identified in 1.1, this paragraph shall state the projectunique identifier assigned to the interface and shall identify the interfacing entities (systems, configuration items, users, etc.) by name, number, version, and documentation references, as applicable. The identification shall state which entities have fixed interface characteristics (and therefore impose interface requirements on interfacing entities) and which are being developed or modified (thus having interface ...
RATIONALE: Converted from IDD.html.md heading.

[REQUIREMENT]
UID: REQ-371
STATUS: Draft
TITLE: 3.x (Project unique identifier of interface).
STATEMENT: This paragraph (beginning with 3.2) shall identify an interface by project unique identifier, shall briefly identify the interfacing entities, and shall be divided into subparagraphs as needed to describe the interface characteristics of one or both of the interfacing entities. If a given interfacing entity is not covered by this IDD (for example, an external system) but its interface characteristics need to be mentioned to describe interfacing entities that are, these characteristics shall b...
RATIONALE: Converted from IDD.html.md heading.

[REQUIREMENT]
UID: REQ-372
STATUS: Draft
TITLE: 4. Requirements traceability.
STATEMENT: This paragraph shall contain: 1. Traceability from each interfacing entity covered by this IDD to the system or CSCI requirements addressed by the entity's interface design. 2. Traceability from each system or CSCI requirement that affects an interface covered in this IDD to the interfacing entities that address it.
RATIONALE: Converted from IDD.html.md heading.

[REQUIREMENT]
UID: REQ-373
STATUS: Draft
TITLE: 5. Notes.
STATEMENT: This section shall contain any general information that aids in understanding this document (e.g., background information, glossary, rationale). This section shall include an alphabetical listing of all acronyms, abbreviations, and their meanings as used in this document and a list of any terms and definitions needed to understand this document.
RATIONALE: Converted from IDD.html.md heading.

[REQUIREMENT]
UID: REQ-374
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from IDD.html.md heading.
