[DOCUMENT]
TITLE: STD.html

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-135
STATUS: Draft
TITLE: 1. Scope.
STATEMENT: This section shall be divided into the following paragraphs.
RATIONALE: Converted from STD.html.md heading.

[REQUIREMENT]
UID: REQ-136
STATUS: Draft
TITLE: 1.1 Identification.
STATEMENT: This paragraph shall contain a full identification of the system and the software to which this document applies, including, as applicable, identification number(s), title(s), abbreviation(s), version number(s), and release number(s).
RATIONALE: Converted from STD.html.md heading.

[REQUIREMENT]
UID: REQ-137
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from STD.html.md heading.

[REQUIREMENT]
UID: REQ-138
STATUS: Draft
TITLE: 1.3 Document overview.
STATEMENT: This paragraph shall summarize the purpose and contents of this document and shall describe any security or privacy considerations associated with its use.
RATIONALE: Converted from STD.html.md heading.

[REQUIREMENT]
UID: REQ-139
STATUS: Draft
TITLE: 2. Referenced documents.
STATEMENT: This section shall list the number, title, revision, and date of all documents referenced in this document. This section shall also identify the source for all documents not available through normal Government stocking activities.
RATIONALE: Converted from STD.html.md heading.

[REQUIREMENT]
UID: REQ-140
STATUS: Draft
TITLE: 3. Test preparations.
STATEMENT: This section shall be divided into the following paragraphs. Safety precautions, marked by WARNING or CAUTION, and security and privacy considerations shall be included as applicable.
RATIONALE: Converted from STD.html.md heading.

[REQUIREMENT]
UID: REQ-141
STATUS: Draft
TITLE: 3.x (Project unique identifier of a test).
STATEMENT: This paragraph shall identify a test by projectunique identifier, shall provide a brief description, and shall be divided into the following subparagraphs. When the information required duplicates information previously specified for another test, that information may be referenced rather than repeated.
RATIONALE: Converted from STD.html.md heading.

[REQUIREMENT]
UID: REQ-142
STATUS: Draft
TITLE: 3.x.1 Hardware preparation.
STATEMENT: This paragraph shall describe the procedures necessary to prepare the hardware for the test. Reference may be made to published operating manuals for these procedures. The following shall be provided, as applicable: 1. The specific hardware to be used, identified by name and, if applicable, number 2. Any switch settings and cabling necessary to connect the hardware 3. One or more diagrams to show hardware, interconnecting control, and data paths 4. Stepbystep instructions for placing the hard...
RATIONALE: Converted from STD.html.md heading.

[REQUIREMENT]
UID: REQ-143
STATUS: Draft
TITLE: 3.x.2 Software preparation.
STATEMENT: This paragraph shall describe the procedures necessary to prepare the item(s) under test and any related software, including data, for the test. Reference may be made to published software manuals for these procedures. The following information shall be provided, as applicable: 1. The specific software to be used in the test 2. The storage medium of the item(s) under test (e.g., magnetic tape, diskette) 3. The storage medium of any related software (e.g., simulators, test drivers, databases) ...
RATIONALE: Converted from STD.html.md heading.

[REQUIREMENT]
UID: REQ-144
STATUS: Draft
TITLE: 3.x.3 Other pre test preparations.
STATEMENT: This paragraph shall describe any other pretest personnel actions, preparations, or procedures necessary to perform the test.
RATIONALE: Converted from STD.html.md heading.

[REQUIREMENT]
UID: REQ-145
STATUS: Draft
TITLE: 4. Test descriptions.
STATEMENT: This section shall be divided into the following paragraphs. Safety precautions, marked by WARNING or CAUTION, and security and privacy considerations shall be included as applicable.
RATIONALE: Converted from STD.html.md heading.

[REQUIREMENT]
UID: REQ-146
STATUS: Draft
TITLE: 4.x (Project unique identifier of a test).
STATEMENT: This paragraph shall identify a test by project unique identifier and shall be divided into the following subparagraphs. When the required information duplicates information previously provided, that information may be referenced rather than repeated.
RATIONALE: Converted from STD.html.md heading.

[REQUIREMENT]
UID: REQ-147
STATUS: Draft
TITLE: 4.x.y (Projectunique identifier of a test case).
STATEMENT: This paragraph shall identify a test case by project unique identifier, state its purpose, and provide a brief description. The following subparagraphs shall provide a detailed description of the test case.
RATIONALE: Converted from STD.html.md heading.

[REQUIREMENT]
UID: REQ-148
STATUS: Draft
TITLE: 4.x.y.1 Requirements addressed.
STATEMENT: This paragraph shall identify the CSCI or system requirements addressed by the test case. (Alternatively, this information may be provided in 5.a.)
RATIONALE: Converted from STD.html.md heading.

[REQUIREMENT]
UID: REQ-149
STATUS: Draft
TITLE: 4.x.y.2 Prerequisite conditions.
STATEMENT: This paragraph shall identify any prerequisite conditions that must be established prior to performing the test case. The following considerations shall be discussed, as applicable: 1. Hardware and software configuration 2. Flags, initial breakpoints, pointers, control parameters, or initial data to be set/reset prior to test commencement 3. Preset hardware conditions or electrical states necessary to run the test case 4. Initial conditions to be used in making timing measurements 5. Conditio...
RATIONALE: Converted from STD.html.md heading.

[REQUIREMENT]
UID: REQ-150
STATUS: Draft
TITLE: 4.x.y.3 Test inputs.
STATEMENT: This paragraph shall describe the test inputs necessary for the test case. The following shall be provided, as applicable: 1. Name, purpose, and description (e.g., range of values, accuracy) of each test input 2. Source of the test input and the method to be used for selecting the test input 3. Whether the test input is real or simulated 4. Time or event sequence of test input 5. The manner in which the input data will be controlled to: 1. Test the item(s) with a minimum/reasonable number of ...
RATIONALE: Converted from STD.html.md heading.

[REQUIREMENT]
UID: REQ-151
STATUS: Draft
TITLE: 4.x.y.4 Expected test results.
STATEMENT: This paragraph shall identify all expected test results for the test case. Both intermediate and final test results shall be provided, as applicable.
RATIONALE: Converted from STD.html.md heading.

[REQUIREMENT]
UID: REQ-152
STATUS: Draft
TITLE: 4.x.y.5 Criteria for evaluating results.
STATEMENT: This paragraph shall identify the criteria to be used for evaluating the intermediate and final results of the test case. For each test result, the following information shall be provided, as applicable: 1. The range or accuracy over which an output can vary and still be acceptable 2. Minimum number of combinations or alternatives of input and output conditions that constitute an acceptable test result 3. Maximum/minimum allowable test duration, in terms of time or number of events 4. Maximum...
RATIONALE: Converted from STD.html.md heading.

[REQUIREMENT]
UID: REQ-153
STATUS: Draft
TITLE: 4.x.y.6 Test procedure.
STATEMENT: This paragraph shall define the test procedure for the test case. The test procedure shall be defined as a series of individually numbered steps listed sequentially in the order in which the steps are to be performed. For convenience in document maintenance, the test procedures may be included as an appendix and referenced in this paragraph. The appropriate level of detail in each test procedure depends on the type of software being tested. For some software, each keystroke may be a separate ...
RATIONALE: Converted from STD.html.md heading.

[REQUIREMENT]
UID: REQ-154
STATUS: Draft
TITLE: 4.x.y.7 Assumptions and constraints.
STATEMENT: This paragraph shall identify any assumptions made and constraints or limitations imposed in the description of the test case due to system or test conditions, such as limitations on timing, interfaces, equipment, personnel, and database/data files. If waivers or exceptions to specified limits and parameters are approved, they shall be identified and this paragraph shall address their effects and impacts upon the test case.
RATIONALE: Converted from STD.html.md heading.

[REQUIREMENT]
UID: REQ-155
STATUS: Draft
TITLE: 5. Requirements traceability.
STATEMENT: This paragraph shall contain: 1. Traceability from each test case in this STD to the system or CSCI requirements it addresses. If a test case addresses multiple requirements, traceability from each set of test procedure steps to the requirement(s) addressed. (Alternatively, this traceability may be provided in 4.x.y.1.) 2. Traceability from each system or CSCI requirement covered by this STD to the test case(s) that address it. For CSCI testing, traceability from each CSCI requirement in the ...
RATIONALE: Converted from STD.html.md heading.

[REQUIREMENT]
UID: REQ-156
STATUS: Draft
TITLE: 6. Notes.
STATEMENT: This section shall contain any general information that aids in understanding this document (e.g., background information, glossary, rationale). This section shall include an alphabetical listing of all acronyms, abbreviations, and their meanings as used in this document and a list of any terms and definitions needed to understand this document.
RATIONALE: Converted from STD.html.md heading.

[REQUIREMENT]
UID: REQ-157
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from STD.html.md heading.
