[DOCUMENT]
TITLE: OCD.html

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-450
STATUS: Draft
TITLE: 1. Scope.
STATEMENT: This section shall be divided into the following paragraphs.
RATIONALE: Converted from OCD.html.md heading.

[REQUIREMENT]
UID: REQ-451
STATUS: Draft
TITLE: 1.1 Identification.
STATEMENT: This paragraph shall contain a full identification of the system to which this document applies, including, as applicable, identification number(s), title(s), abbreviation(s), version number(s), and release number(s).
RATIONALE: Converted from OCD.html.md heading.

[REQUIREMENT]
UID: REQ-452
STATUS: Draft
TITLE: 1.2 System overview.
STATEMENT: This paragraph shall briefly state the purpose of the system to which this document applies. It shall describe the general nature of the system; summarize the history of system development, operation, and maintenance; identify the project sponsor, acquirer, user, developer, and support agencies; identify current and planned operating sites; and list other relevant documents.
RATIONALE: Converted from OCD.html.md heading.

[REQUIREMENT]
UID: REQ-453
STATUS: Draft
TITLE: 1.3 Document overview.
STATEMENT: This paragraph shall summarize the purpose and contents of this document and shall describe any security or privacy considerations associated with its use.
RATIONALE: Converted from OCD.html.md heading.

[REQUIREMENT]
UID: REQ-454
STATUS: Draft
TITLE: 2. Referenced documents.
STATEMENT: This section shall list the number, title, revision, and date of all documents referenced in this document. This section shall also identify the source for all documents not available through normal Government stocking activities.
RATIONALE: Converted from OCD.html.md heading.

[REQUIREMENT]
UID: REQ-455
STATUS: Draft
TITLE: 3. Current system or situation.
STATEMENT: This section shall be divided into the following paragraphs to describe the system or situation as it currently exists.
RATIONALE: Converted from OCD.html.md heading.

[REQUIREMENT]
UID: REQ-456
STATUS: Draft
TITLE: 3.1 Background, objectives, and scope.
STATEMENT: This paragraph shall describe the background, mission or objectives, and scope of the current system or situation.
RATIONALE: Converted from OCD.html.md heading.

[REQUIREMENT]
UID: REQ-457
STATUS: Draft
TITLE: 3.2 Operational policies and constraints.
STATEMENT: This paragraph shall describe any operational policies and constraints that apply to the current system or situation.
RATIONALE: Converted from OCD.html.md heading.

[REQUIREMENT]
UID: REQ-458
STATUS: Draft
TITLE: 3.3 Description of current system or situation.
STATEMENT: This paragraph shall provide a description of the current system or situation, identifying differences associated with different states or modes of operation (for example, regular, maintenance, training, degraded, emergency, alternativesite, wartime, peacetime). The distinction between states and modes is arbitrary. A system may be described in terms of states only, modes only, states within modes, modes within states, or any other scheme that is useful. If the system operates without states ...
RATIONALE: Converted from OCD.html.md heading.

[REQUIREMENT]
UID: REQ-459
STATUS: Draft
TITLE: 3.4 Users or involved personnel.
STATEMENT: This paragraph shall describe the types of users of the system, or personnel involved in the current situation, including, as applicable, organizational structures, training/skills, responsibilities, activities, and interactions with one another.
RATIONALE: Converted from OCD.html.md heading.

[REQUIREMENT]
UID: REQ-460
STATUS: Draft
TITLE: 3.5 Support concept.
STATEMENT: This paragraph shall provide an overview of the support concept for the current system, including, as applicable to this document, support agency(ies); facilities; equipment; support software; repair/replacement criteria; maintenance levels and cycles; and storage, distribution, and supply methods.
RATIONALE: Converted from OCD.html.md heading.

[REQUIREMENT]
UID: REQ-461
STATUS: Draft
TITLE: 4. Justification for and nature of changes.
STATEMENT: This section shall be divided into the following paragraphs.
RATIONALE: Converted from OCD.html.md heading.

[REQUIREMENT]
UID: REQ-462
STATUS: Draft
TITLE: 4.1 Justification for change.
STATEMENT: This paragraph shall: Describe new or modified aspects of user needs, threats, missions, objectives, environments, interfaces, personnel or other factors that require a new or modified system Summarize deficiencies or limitations in the current system or situation that make it unable to respond to these factors
RATIONALE: Converted from OCD.html.md heading.

[REQUIREMENT]
UID: REQ-463
STATUS: Draft
TITLE: 4.2 Description of needed changes.
STATEMENT: This paragraph shall summarize new or modified capabilities/functions, processes, interfaces, or other changes needed to respond to the factors identified in 4.1.
RATIONALE: Converted from OCD.html.md heading.

[REQUIREMENT]
UID: REQ-464
STATUS: Draft
TITLE: 4.3 Priorities among the changes.
STATEMENT: This paragraph shall identify priorities among the needed changes. It shall, for example, identify each change as essential, desirable, or optional, and prioritize the desirable and optional changes.
RATIONALE: Converted from OCD.html.md heading.

[REQUIREMENT]
UID: REQ-465
STATUS: Draft
TITLE: 4.4 Changes considered but not included.
STATEMENT: This paragraph shall identify changes considered but not included in 4.2, and rationale for not including them.
RATIONALE: Converted from OCD.html.md heading.

[REQUIREMENT]
UID: REQ-466
STATUS: Draft
TITLE: 4.5 Assumptions and constraints.
STATEMENT: This paragraph shall identify any assumptions and constraints applicable to the changes identified in this section.
RATIONALE: Converted from OCD.html.md heading.

[REQUIREMENT]
UID: REQ-467
STATUS: Draft
TITLE: 5. Concept for a new or modified system.
STATEMENT: This section shall be divided into the following paragraphs to describe a new or modified system.
RATIONALE: Converted from OCD.html.md heading.

[REQUIREMENT]
UID: REQ-468
STATUS: Draft
TITLE: 5.1 Background, objectives, and scope.
STATEMENT: This paragraph shall describe the background, mission or objectives, and scope of the new or modified system.
RATIONALE: Converted from OCD.html.md heading.

[REQUIREMENT]
UID: REQ-469
STATUS: Draft
TITLE: 5.2 Operational policies and constraints.
STATEMENT: This paragraph shall describe any operational policies and constraints that apply to the new or modified system.
RATIONALE: Converted from OCD.html.md heading.

[REQUIREMENT]
UID: REQ-470
STATUS: Draft
TITLE: 5.3 Description of the new or modified system.
STATEMENT: This paragraph shall provide a description of the new or modified system, identifying differences associated with different states or modes of operation (for example, regular, maintenance, training, degraded, emergency, alternativesite, wartime, peacetime). The distinction between states and modes is arbitrary. A system may be described in terms of states only, modes only, states within modes, modes within states, or any other scheme that is useful. If the system operates without states or mo...
RATIONALE: Converted from OCD.html.md heading.

[REQUIREMENT]
UID: REQ-471
STATUS: Draft
TITLE: 5.4 Users/affected personnel.
STATEMENT: This paragraph shall describe the types of users of the new or modified system, including, as applicable, organizational structures, training/skills, responsibilities, and interactions with one another.
RATIONALE: Converted from OCD.html.md heading.

[REQUIREMENT]
UID: REQ-472
STATUS: Draft
TITLE: 5.5 Support concept.
STATEMENT: This paragraph shall provide an overview of the support concept for the new or modified system, including, as applicable, support agency(ies); facilities; equipment; support software; repair/replacement criteria; maintenance levels and cycles; and storage, distribution, and supply methods.
RATIONALE: Converted from OCD.html.md heading.

[REQUIREMENT]
UID: REQ-473
STATUS: Draft
TITLE: 6. Operational scenarios.
STATEMENT: This section shall describe one or more operational scenarios that illustrate the role of the new or modified system, its interaction with users, its interface to other systems, and all states or modes identified for the system. The scenarios shall include events, actions, stimuli, information, interactions, etc., as applicable. Reference may be made to other media, such as videos, to provide part or all of this information.
RATIONALE: Converted from OCD.html.md heading.

[REQUIREMENT]
UID: REQ-474
STATUS: Draft
TITLE: 7. Summary of impacts.
STATEMENT: This section shall be divided into the following paragraphs.
RATIONALE: Converted from OCD.html.md heading.

[REQUIREMENT]
UID: REQ-475
STATUS: Draft
TITLE: 7.1 Operational impacts.
STATEMENT: This paragraph shall describe anticipated operational impacts on the user, acquirer, developer, and support agency(ies). These impacts may include changes in interfaces with computer operating centers; change in procedures; use of new data sources; changes in quantity, type, and timing of data to be input to the system; changes in data retention requirements; and new modes of operation based on peacetime, alert, wartime, or emergency conditions.
RATIONALE: Converted from OCD.html.md heading.

[REQUIREMENT]
UID: REQ-476
STATUS: Draft
TITLE: 7.2 Organizational impacts.
STATEMENT: This paragraph shall describe anticipated organizational impacts on the user, acquirer, developer, and support agency(ies). These impacts may include modification of responsibilities; addition or elimination of responsibilities or positions; need for training or retraining; and changes in number, skill levels, position identifiers, or location of personnel in various modes of operation.
RATIONALE: Converted from OCD.html.md heading.

[REQUIREMENT]
UID: REQ-477
STATUS: Draft
TITLE: 7.3 Impacts during development.
STATEMENT: This paragraph shall describe anticipated impacts on the user, acquirer, developer, and support agency(ies) during the development effort. These impacts may include meetings/discussions regarding the new system; development or modification of databases; training; parallel operation of the new and existing systems; impacts during testing of the new system; and other activities needed to aid or monitor development.
RATIONALE: Converted from OCD.html.md heading.

[REQUIREMENT]
UID: REQ-478
STATUS: Draft
TITLE: 8. Analysis of the proposed system.
STATEMENT: 8. Analysis of the proposed system.
RATIONALE: Converted from OCD.html.md heading.

[REQUIREMENT]
UID: REQ-479
STATUS: Draft
TITLE: 8.1 Summary of advantages.
STATEMENT: This paragraph shall provide a qualitative and quantitative summary of the advantages to be obtained from the new or modified system. This summary shall include new capabilities, enhanced capabilities, and improved performance, as applicable, and their relationship to deficiencies identified in 4.1.
RATIONALE: Converted from OCD.html.md heading.

[REQUIREMENT]
UID: REQ-480
STATUS: Draft
TITLE: 8.2 Summary of disadvantages/limitations.
STATEMENT: This paragraph shall provide a qualitative and quantitative summary of disadvantages or limitations of the new or modified system. These disadvantages and limitations shall include, as applicable, degraded or missing capabilities, degraded or lessthandesired performance, greaterthandesired use of computer hardware resources, undesirable operational impacts, conflicts with user assumptions, and other constraints.
RATIONALE: Converted from OCD.html.md heading.

[REQUIREMENT]
UID: REQ-481
STATUS: Draft
TITLE: 8.3 Alternatives and tradeoffs considered.
STATEMENT: This paragraph shall identify and describe major alternatives considered to the system or its characteristics, the tradeoffs among them, and rationale for the decisions reached.
RATIONALE: Converted from OCD.html.md heading.

[REQUIREMENT]
UID: REQ-482
STATUS: Draft
TITLE: 9. Notes.
STATEMENT: This section shall contain any general information that aids in understanding this document (e.g., background information, glossary, rationale). This section shall include an alphabetical listing of all acronyms, abbreviations, and their meanings as used in this document and a list of any terms and definitions needed to understand this document.
RATIONALE: Converted from OCD.html.md heading.

[REQUIREMENT]
UID: REQ-483
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from OCD.html.md heading.
