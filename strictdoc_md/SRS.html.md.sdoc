[DOCUMENT]
TITLE: SRS.html

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-258
STATUS: Draft
TITLE: 1. Scope.
STATEMENT: This section shall be divided into the following paragraphs.
RATIONALE: Converted from SRS.html.md heading.

[REQUIREMENT]
UID: REQ-259
STATUS: Draft
TITLE: 1.1 Identification.
STATEMENT: This paragraph shall contain a full identification of the system and the software to which this document applies, including, as applicable, identification number(s), title(s), abbreviation(s), version number(s), and release number(s).
RATIONALE: Converted from SRS.html.md heading.

[REQUIREMENT]
UID: REQ-260
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from SRS.html.md heading.

[REQUIREMENT]
UID: REQ-261
STATUS: Draft
TITLE: 1.3 Document overview.
STATEMENT: This paragraph shall summarize the purpose and contents of this document and shall describe any security or privacy considerations associated with its use.
RATIONALE: Converted from SRS.html.md heading.

[REQUIREMENT]
UID: REQ-262
STATUS: Draft
TITLE: 2. Referenced documents.
STATEMENT: This section shall list the number, title, revision, and date of all documents referenced in this specification. This section shall also identify the source for all documents not available through normal Government stocking activities.
RATIONALE: Converted from SRS.html.md heading.

[REQUIREMENT]
UID: REQ-263
STATUS: Draft
TITLE: 3. Requirements.
STATEMENT: This section shall be divided into the following paragraphs to specify the CSCI requirements, that is, those characteristics of the CSCI that are conditions for its acceptance. CSCI requirements are software requirements generated to satisfy the system requirements allocated to this CSCI. Each requirement shall be assigned a projectunique identifier to support testing and traceability and shall be stated in such a way that an objective test can be defined for it. Each requirement shall be ann...
RATIONALE: Converted from SRS.html.md heading.

[REQUIREMENT]
UID: REQ-264
STATUS: Draft
TITLE: 3.1 Required states and modes.
STATEMENT: If the CSCI is required to operate in more than one state or mode having requirements distinct from other states or modes, this paragraph shall identify and define each state and mode. Examples of states and modes include: idle, ready, active, postuse analysis, training, degraded, emergency, backup, wartime, peacetime. The distinction between states and modes is arbitrary. A CSCI may be described in terms of states only, modes only, states within modes, modes within states, or any other schem...
RATIONALE: Converted from SRS.html.md heading.

[REQUIREMENT]
UID: REQ-265
STATUS: Draft
TITLE: 3.2 CSCI capability requirements.
STATEMENT: This paragraph shall be divided into subparagraphs to itemize the requirements associated with each capability of the CSCI. A "capability" is defined as a group of related requirements. The word "capability" may be replaced with "function," "subject," "object," or other term useful for presenting the requirements.
RATIONALE: Converted from SRS.html.md heading.

[REQUIREMENT]
UID: REQ-266
STATUS: Draft
TITLE: 3.2.x (CSCI capability).
STATEMENT: This paragraph shall identify a required CSCI capability and shall itemize the requirements associated with the capability. If the capability can be more clearly specified by dividing it into constituent capabilities, the constituent capabilities shall be specified in subparagraphs. The requirements shall specify required behavior of the CSCI and shall include applicable parameters, such as response times, throughput times, other timing constraints, sequencing, accuracy, capacities (how much/...
RATIONALE: Converted from SRS.html.md heading.

[REQUIREMENT]
UID: REQ-267
STATUS: Draft
TITLE: 3.3 CSCI external interface requirements.
STATEMENT: This paragraph shall be divided into subparagraphs to specify the requirements, if any, for the CSCI's external interfaces. This paragraph may reference one or more Interface Requirements Specifications (IRSs) or other documents containing these requirements.
RATIONALE: Converted from SRS.html.md heading.

[REQUIREMENT]
UID: REQ-268
STATUS: Draft
TITLE: 3.3.1 Interface identification and diagrams.
STATEMENT: This paragraph shall identify the required external interfaces of the CSCI (that is, relationships with other entities that involve sharing, providing or exchanging data). The identification of each interface shall include a projectunique identifier and shall designate the interfacing entities (systems, configuration items, users, etc.) by name, number, version, and documentation references, as applicable. The identification shall state which entities have fixed interface characteristics (and...
RATIONALE: Converted from SRS.html.md heading.

[REQUIREMENT]
UID: REQ-269
STATUS: Draft
TITLE: 3.3.x (Project unique identifier of interface).
STATEMENT: This paragraph (beginning with 3.3.2) shall identify a CSCI external interface by project unique identifier, shall briefly identify the interfacing entities, and shall be divided into subparagraphs as needed to state the requirements imposed on the CSCI to achieve the interface. Interface characteristics of the other entities involved in the interface shall be stated as assumptions or as "When [the entity not covered] does this, the CSCI shall...," not as requirements on the other entities. T...
RATIONALE: Converted from SRS.html.md heading.

[REQUIREMENT]
UID: REQ-270
STATUS: Draft
TITLE: 3.4 CSCI internal interface requirements.
STATEMENT: This paragraph shall specify the requirements, if any, imposed on interfaces internal to the CSCI. If all internal interfaces are left to the design, this fact shall be so stated. If such requirements are to be imposed, paragraph 3.3 of this DID provides a list of topics to be considered.
RATIONALE: Converted from SRS.html.md heading.

[REQUIREMENT]
UID: REQ-271
STATUS: Draft
TITLE: 3.5 CSCI internal data requirements.
STATEMENT: This paragraph shall specify the requirements, if any, imposed on data internal to the CSCI. Included shall be requirements, if any, on databases and data files to be included in the CSCI. If all decisions about internal data are left to the design, this fact shall be so stated. If such requirements are to be imposed, paragraphs 3.3.x.c and 3.3.x.d of this DID provide a list of topics to be considered.
RATIONALE: Converted from SRS.html.md heading.

[REQUIREMENT]
UID: REQ-272
STATUS: Draft
TITLE: 3.6 Adaptation requirements.
STATEMENT: This paragraph shall specify the requirements, if any, concerning installationdependent data to be provided by the CSCI (such as sitedependent latitude and longitude or sitedependent state tax codes) and operational parameters that the CSCI is required to use that may vary according to operational needs (such as parameters indicating operationdependent targeting constants or data recording).
RATIONALE: Converted from SRS.html.md heading.

[REQUIREMENT]
UID: REQ-273
STATUS: Draft
TITLE: 3.7 Safety requirements.
STATEMENT: This paragraph shall specify the CSCI requirements, if any, concerned with preventing or minimizing unintended hazards to personnel, property, and the physical environment. Examples include safeguards the CSCI must provide to prevent inadvertent actions (such as accidentally issuing an "auto pilot off" command) and nonactions (such as failure to issue an intended "auto pilot off" command). This paragraph shall include the CSCI requirements, if any, regarding nuclear components of the system, ...
RATIONALE: Converted from SRS.html.md heading.

[REQUIREMENT]
UID: REQ-274
STATUS: Draft
TITLE: 3.8 Security and privacy requirements.
STATEMENT: This paragraph shall specify the CSCI requirements, if any, concerned with maintaining security and privacy. These requirements shall include, as applicable, the security/privacy environment in which the CSCI must operate, the type and degree of security or privacy to be provided, the security/privacy risks the CSCI must withstand, required safeguards to reduce those risks, the security/privacy policy that must be met, the security/privacy accountability the CSCI must provide, and the criteri...
RATIONALE: Converted from SRS.html.md heading.

[REQUIREMENT]
UID: REQ-275
STATUS: Draft
TITLE: 3.9 CSCI environment requirements.
STATEMENT: This paragraph shall specify the requirements, if any, regarding the environment in which the CSCI must operate. Examples include the computer hardware and operating system on which the CSCI must run. (Additional requirements concerning computer resources are given in the next paragraph.)
RATIONALE: Converted from SRS.html.md heading.

[REQUIREMENT]
UID: REQ-276
STATUS: Draft
TITLE: 3.10 Computer resource requirements.
STATEMENT: This paragraph shall be divided into the following subparagraphs.
RATIONALE: Converted from SRS.html.md heading.

[REQUIREMENT]
UID: REQ-277
STATUS: Draft
TITLE: 3.10.1 Computer hardware requirements.
STATEMENT: This paragraph shall specify the requirements, if any, regarding computer hardware that must be used by the CSCI. The requirements shall include, as applicable, number of each type of equipment, type, size, capacity, and other required characteristics of processors, memory, input/output devices, auxiliary storage, communications/network equipment, and other required equipment.
RATIONALE: Converted from SRS.html.md heading.

[REQUIREMENT]
UID: REQ-278
STATUS: Draft
TITLE: 3.10.2 Computer hardware resource utilization requirements.
STATEMENT: This paragraph shall specify the requirements, if any, on the CSCI's computer hardware resource utilization, such as maximum allowable use of processor capacity, memory capacity, input/output device capacity, auxiliary storage device capacity, and communications/network equipment capacity. The requirements (stated, for example, as percentages of the capacity of each computer hardware resource) shall include the conditions, if any, under which the resource utilization is to be measured.
RATIONALE: Converted from SRS.html.md heading.

[REQUIREMENT]
UID: REQ-279
STATUS: Draft
TITLE: 3.10.3 Computer software requirements.
STATEMENT: This paragraph shall specify the requirements, if any, regarding computer software that must be used by, or incorporated into, the CSCI. Examples include operating systems, database management systems, communications/ network software, utility software, input and equipment simulators, test software, and manufacturing software. The correct nomenclature, version, and documentation references of each such software item shall be provided.
RATIONALE: Converted from SRS.html.md heading.

[REQUIREMENT]
UID: REQ-280
STATUS: Draft
TITLE: 3.10.4 Computer communications requirements.
STATEMENT: This paragraph shall specify the additional requirements, if any, concerning the computer communications that must be used by the CSCI. Examples include geographic locations to be linked; configuration and network topology; transmission techniques; data transfer rates; gateways; required system use times; type and volume of data to be transmitted/received; time boundaries for transmission/ reception/response; peak volumes of data; and diagnostic features.
RATIONALE: Converted from SRS.html.md heading.

[REQUIREMENT]
UID: REQ-281
STATUS: Draft
TITLE: 3.11 Software quality factors.
STATEMENT: This paragraph shall specify the CSCI requirements, if any, concerned with software quality factors identified in the contract or derived from a higher level specification. Examples include quantitative requirements regarding CSCI functionality (the ability to perform all required functions), reliability (the ability to perform with correct, consistent results), maintainability (the ability to be easily corrected), availability (the ability to be accessed and operated when needed), flexibilit...
RATIONALE: Converted from SRS.html.md heading.

[REQUIREMENT]
UID: REQ-282
STATUS: Draft
TITLE: 3.12 Design and implementation constraints.
STATEMENT: This paragraph shall specify the requirements, if any, that constrain the design and implementation of the CSCI. These requirements may be specified by reference to appropriate commercial or military standards and specifications. Examples include requirements concerning: Use of a particular CSCI architecture or requirements on the architecture, such as required databases or other software units; use of standard, military, or existing components; or use of Government/acquirerfurnished property...
RATIONALE: Converted from SRS.html.md heading.

[REQUIREMENT]
UID: REQ-283
STATUS: Draft
TITLE: 3.13 Personnelrelated requirements.
STATEMENT: This paragraph shall specify the CSCI requirements, if any, included to accommodate the number, skill levels, duty cycles, training needs, or other information about the personnel who will use or support the CSCI. Examples include requirements for number of simultaneous users and for builtin help or training features. Also included shall be the human factors engineering requirements, if any, imposed on the CSCI. These requirements shall include, as applicable, considerations for the capabilit...
RATIONALE: Converted from SRS.html.md heading.

[REQUIREMENT]
UID: REQ-284
STATUS: Draft
TITLE: 3.14 Trainingrelated requirements.
STATEMENT: This paragraph shall specify the CSCI requirements, if any, pertaining to training. Examples include training software to be included in the CSCI.
RATIONALE: Converted from SRS.html.md heading.

[REQUIREMENT]
UID: REQ-285
STATUS: Draft
TITLE: 3.15 Logisticsrelated requirements.
STATEMENT: This paragraph shall specify the CSCI requirements, if any, concerned with logistics considerations. These considerations may include: system maintenance, software support, system transportation modes, supply system requirements, impact on existing facilities, and impact on existing equipment.
RATIONALE: Converted from SRS.html.md heading.

[REQUIREMENT]
UID: REQ-286
STATUS: Draft
TITLE: 3.16 Other requirements.
STATEMENT: This paragraph shall specify additional CSCI requirements, if any, not covered in the previous paragraphs.
RATIONALE: Converted from SRS.html.md heading.

[REQUIREMENT]
UID: REQ-287
STATUS: Draft
TITLE: 3.17 Packaging requirements.
STATEMENT: This section shall specify the requirements, if any, for packaging, labeling, and handling the CSCI for delivery (for example, delivery on 8 track magnetic tape labelled and packaged in a certain way). Applicable military specifications and standards may be referenced if appropriate.
RATIONALE: Converted from SRS.html.md heading.

[REQUIREMENT]
UID: REQ-288
STATUS: Draft
TITLE: 3.18 Precedence and criticality of requirements.
STATEMENT: This paragraph shall specify, if applicable, the order of precedence, criticality, or assigned weights indicating the relative importance of the requirements in this specification. Examples include identifying those requirements deemed critical to safety, to security, or to privacy for purposes of singling them out for special treatment. If all requirements have equal weight, this paragraph shall so state.
RATIONALE: Converted from SRS.html.md heading.

[REQUIREMENT]
UID: REQ-289
STATUS: Draft
TITLE: 4. Qualification provisions.
STATEMENT: This section shall define a set of qualification methods and shall specify for each requirement in Section 3 the method(s) to be used to ensure that the requirement has been met. A table may be used to present this information, or each requirement in Section 3 may be annotated with the method(s) to be used. Qualification methods may include: Demonstration: The operation of the CSCI, or a part of the CSCI, that relies on observable functional operation not requiring the use of instrumentation,...
RATIONALE: Converted from SRS.html.md heading.

[REQUIREMENT]
UID: REQ-290
STATUS: Draft
TITLE: 5. Requirements traceability.
STATEMENT: This paragraph shall contain: Traceability from each CSCI requirement in this specification to the system (or subsystem, if applicable) requirements it addresses. (Alternatively, this traceability may be provided by annotating each requirement in Section 3.) Note: Each level of system refinement may result in requirements not directly traceable to higherlevel requirements. For example, a system architectural design that creates multiple CSCIs may result in requirements about how the CSCIs wil...
RATIONALE: Converted from SRS.html.md heading.

[REQUIREMENT]
UID: REQ-291
STATUS: Draft
TITLE: 6. Notes.
STATEMENT: This section shall contain any general information that aids in understanding this specification (e.g., background information, glossary, rationale). This section shall include an alphabetical listing of all acronyms, abbreviations, and their meanings as used in this document and a list of any terms and definitions needed to understand this document.
RATIONALE: Converted from SRS.html.md heading.

[REQUIREMENT]
UID: REQ-292
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SRS.html.md heading.
