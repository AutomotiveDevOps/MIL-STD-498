[DOCUMENT]
TITLE: SDP

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-196
STATUS: Draft
TITLE: 1. Scope.
STATEMENT: This section shall be divided into the following paragraphs.
RATIONALE: Converted from SDP.html heading.

[REQUIREMENT]
UID: REQ-197
STATUS: Draft
TITLE: 1.1 Identification.
STATEMENT: This paragraph shall contain a full identification of the system and the software to which this document applies, including, as applicable, identification number(s), title(s), abbreviation(s), version number(s), and release number(s).
RATIONALE: Converted from SDP.html heading.

[REQUIREMENT]
UID: REQ-198
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from SDP.html heading.

[REQUIREMENT]
UID: REQ-199
STATUS: Draft
TITLE: 1.3 Document overview.
STATEMENT: This paragraph shall summarize the purpose and contents of this document and shall describe any security or privacy considerations associated with its use.
RATIONALE: Converted from SDP.html heading.

[REQUIREMENT]
UID: REQ-200
STATUS: Draft
TITLE: 1.4 Relationship to other plans.
STATEMENT: This paragraph shall describe the relationship, if any, of the SDP to other project management plans.
RATIONALE: Converted from SDP.html heading.

[REQUIREMENT]
UID: REQ-201
STATUS: Draft
TITLE: 2. Referenced documents.
STATEMENT: This section shall list the number, title, revision, and date of all documents referenced in this plan. This section shall also identify the source for all documents not available through normal Government stocking activities.
RATIONALE: Converted from SDP.html heading.

[REQUIREMENT]
UID: REQ-202
STATUS: Draft
TITLE: 3. Overview of required work.
STATEMENT: This section shall be divided into paragraphs as needed to establish the context for the planning described in later sections. It shall include, as applicable, an overview of:Requirements and constraints on the system and software to be developedRequirements and constraints on project documentationPosition of the project in the system life cycleThe selected program/acquisition strategy or any requirements or constraints on itRequirements and constraints on project schedules and resourcesOther...
RATIONALE: Converted from SDP.html heading.

[REQUIREMENT]
UID: REQ-203
STATUS: Draft
TITLE: 4. Plans for performing general software development activities.
STATEMENT: This section shall be divided into the following paragraphs. Provisions corresponding to nonrequired activities may be satisfied by the words "Not applicable." If different builds or different software on the project require different planning, these differences shall be noted in the paragraphs. In addition to the content specified below, each paragraph shall identify applicable risks/uncertainties and plans for dealing with them.
RATIONALE: Converted from SDP.html heading.

[REQUIREMENT]
UID: REQ-204
STATUS: Draft
TITLE: 4.1 Software development process.
STATEMENT: This paragraph shall describe the software development process to be used. The planning shall cover all contractual clauses concerning this topic, identifying planned builds, if applicable, their objectives, and the software development activities to be performed in each build.
RATIONALE: Converted from SDP.html heading.

[REQUIREMENT]
UID: REQ-205
STATUS: Draft
TITLE: 4.2 General plans for software development.
STATEMENT: This paragraph shall be divided into the following subparagraphs.
RATIONALE: Converted from SDP.html heading.

[REQUIREMENT]
UID: REQ-206
STATUS: Draft
TITLE: 4.2.1 Software development methods.
STATEMENT: This paragraph shall describe or reference the software development methods to be used. Included shall be descriptions of the manual and automated tools and procedures to be used in support of these methods. The methods shall cover all contractual clauses concerning this topic. Reference may be made to other paragraphs in this plan if the methods are better described in context with the activities to which they will be applied.
RATIONALE: Converted from SDP.html heading.

[REQUIREMENT]
UID: REQ-207
STATUS: Draft
TITLE: 4.2.2 Standards for software products.
STATEMENT: This paragraph shall describe or reference the standards to be followed for representing requirements, design, code, test cases, test procedures, and test results. The standards shall cover all contractual clauses concerning this topic. Reference may be made to other paragraphs in this plan if the standards are better described in context with the activities to which they will be applied. Standards for code shall be provided for each programming language to be used. They shall include at a mi...
RATIONALE: Converted from SDP.html heading.

[REQUIREMENT]
UID: REQ-208
STATUS: Draft
TITLE: 4.2.3 Reusable software products.
STATEMENT: This paragraph shall be divided into the following subparagraphs.
RATIONALE: Converted from SDP.html heading.

[REQUIREMENT]
UID: REQ-209
STATUS: Draft
TITLE: 4.2.3.1 Incorporating reusable software products.
STATEMENT: This paragraph shall describe the approach to be followed for identifying, evaluating, and incorporating reusable software products, including the scope of the search for such products and the criteria to be used for their evaluation. It shall cover all contractual clauses concerning this topic. Candidate or selected reusable software products known at the time this plan is prepared or updated shall be identified and described, together with benefits, drawbacks, and restrictions, as applicabl...
RATIONALE: Converted from SDP.html heading.

[REQUIREMENT]
UID: REQ-210
STATUS: Draft
TITLE: 4.2.3.2 Developing reusable software products.
STATEMENT: This paragraph shall describe the approach to be followed for identifying, evaluating, and reporting opportunities for developing reusable software products. It shall cover all contractual clauses concerning this topic.
RATIONALE: Converted from SDP.html heading.

[REQUIREMENT]
UID: REQ-211
STATUS: Draft
TITLE: 4.2.4 Handling of critical requirements.
STATEMENT: This paragraph shall be divided into the following subparagraphs to describe the approach to be followed for handling requirements designated critical. The planning in each subparagraph shall cover all contractual clauses concerning the identified topic.4.2.4.1 Safety assurance4.2.4.2 Security assurance4.2.4.3 Privacy assurance4.2.4.4 Assurance of other critical requirements
RATIONALE: Converted from SDP.html heading.

[REQUIREMENT]
UID: REQ-212
STATUS: Draft
TITLE: 4.2.5 Computer hardware resource utilization.
STATEMENT: This paragraph shall describe the approach to be followed for allocating computer hardware resources and monitoring their utilization. It shall cover all contractual clauses concerning this topic.
RATIONALE: Converted from SDP.html heading.

[REQUIREMENT]
UID: REQ-213
STATUS: Draft
TITLE: 4.2.6 Recording rationale.
STATEMENT: This paragraph shall describe the approach to be followed for recording rationale that will be useful to the support agency for key decisions made on the project. It shall interpret the term "key decisions" for the project and state where the rationale are to be recorded. It shall cover all contractual clauses concerning this topic.
RATIONALE: Converted from SDP.html heading.

[REQUIREMENT]
UID: REQ-214
STATUS: Draft
TITLE: 4.2.7 Access for acquirer review.
STATEMENT: This paragraph shall describe the approach to be followed for providing the acquirer or its authorized representative access to developer and subcontractor facilities for review of software products and activities. It shall cover all contractual clauses concerning this topic.
RATIONALE: Converted from SDP.html heading.

[REQUIREMENT]
UID: REQ-215
STATUS: Draft
TITLE: 5. Plans for performing detailed software development activities.
STATEMENT: This section shall be divided into the following paragraphs. Provisions corresponding to nonrequired activities may be satisfied by the words "Not applicable." If different builds or different software on the project require different planning, these differences shall be noted in the paragraphs. The discussion of each activity shall include the approach (methods/procedures/tools) to be applied to: 1) the analysis or other technical tasks involved, 2) the recording of results, and 3) the prepa...
RATIONALE: Converted from SDP.html heading.

[REQUIREMENT]
UID: REQ-216
STATUS: Draft
TITLE: 5.1 Project planning and oversight.
STATEMENT: This paragraph shall be divided into the following subparagraphs to describe the approach to be followed for project planning and oversight. The planning in each subparagraph shall cover all contractual clauses regarding the identified topic.5.1.1 Software development planning (covering updates to this plan)5.1.2 CSCI test planning5.1.3 System test planning5.1.4 Software installation planning5.1.5 Software transition planning5.1.6 Following and updating plans, including the intervals for mana...
RATIONALE: Converted from SDP.html heading.

[REQUIREMENT]
UID: REQ-217
STATUS: Draft
TITLE: 5.2 Establishing a software development environment.
STATEMENT: This paragraph shall be divided into the following subparagraphs to describe the approach to be followed for establishing, controlling, and maintaining a software development environment. The planning in each subparagraph shall cover all contractual clauses regarding the identified topic.5.2.1 Software engineering environment5.2.2 Software test environment5.2.3 Software development library5.2.4 Software development files5.2.5 Nondeliverable software
RATIONALE: Converted from SDP.html heading.

[REQUIREMENT]
UID: REQ-218
STATUS: Draft
TITLE: 5.3 System requirements analysis.
STATEMENT: This paragraph shall be divided into the following subparagraphs to describe the approach to be followed for participating in system requirements analysis. The planning in each subparagraph shall cover all contractual clauses regarding the identified topic.5.3.1 Analysis of user input5.3.2 Operational concept5.3.3 System requirements
RATIONALE: Converted from SDP.html heading.

[REQUIREMENT]
UID: REQ-219
STATUS: Draft
TITLE: 5.4 System design.
STATEMENT: This paragraph shall be divided into the following subparagraphs to describe the approach to be followed for participating in system design. The planning in each subparagraph shall cover all contractual clauses regarding the identified topic.5.4.1 Systemwide design decisions5.4.2 System architectural design
RATIONALE: Converted from SDP.html heading.

[REQUIREMENT]
UID: REQ-220
STATUS: Draft
TITLE: 5.5 Software requirements analysis.
STATEMENT: This paragraph shall describe the approach to be followed for software requirements analysis. The approach shall cover all contractual clauses concerning this topic.
RATIONALE: Converted from SDP.html heading.

[REQUIREMENT]
UID: REQ-221
STATUS: Draft
TITLE: 5.6 Software design.
STATEMENT: This paragraph shall be divided into the following subparagraphs to describe the approach to be followed for software design. The planning in each subparagraph shall cover all contractual clauses regarding the identified topic.5.6.1 CSCIwide design decisions5.6.2 CSCI architectural design5.6.3 CSCI detailed design
RATIONALE: Converted from SDP.html heading.

[REQUIREMENT]
UID: REQ-222
STATUS: Draft
TITLE: 5.7 Software implementation and unit testing.
STATEMENT: This paragraph shall be divided into the following subparagraphs to describe the approach to be followed for software implementation and unit testing. The planning in each subparagraph shall cover all contractual clauses regarding the identified topic.5.7.1 Software implementation5.7.2 Preparing for unit testing5.7.3 Performing unit testing5.7.4 Revision and retesting5.7.5 Analyzing and recording unit test results
RATIONALE: Converted from SDP.html heading.

[REQUIREMENT]
UID: REQ-223
STATUS: Draft
TITLE: 5.8 Unit integration and testing.
STATEMENT: This paragraph shall be divided into the following subparagraphs to describe the approach to be followed for unit integration and testing. The planning in each subparagraph shall cover all contractual clauses regarding the identified topic.5.8.1 Preparing for unit integration and testing5.8.2 Performing unit integration and testing5.8.3 Revision and retesting5.8.4 Analyzing and recording unit integration and test results
RATIONALE: Converted from SDP.html heading.

[REQUIREMENT]
UID: REQ-224
STATUS: Draft
TITLE: 5.9 CSCI qualification testing.
STATEMENT: This paragraph shall be divided into the following subparagraphs to describe the approach to be followed for CSCI qualification testing. The planning in each subparagraph shall cover all contractual clauses regarding the identified topic.5.9.1 Independence in CSCI qualification testing5.9.2 Testing on the target computer system5.9.3 Preparing for CSCI qualification testing5.9.4 Dry run of CSCI qualification testing5.9.5 Performing CSCI qualification testing5.9.6 Revision and retesting5.9.7 An...
RATIONALE: Converted from SDP.html heading.

[REQUIREMENT]
UID: REQ-225
STATUS: Draft
TITLE: 5.10 CSCI/HWCI integration and testing.
STATEMENT: This paragraph shall be divided into the following subparagraphs to describe the approach to be followed for participating in CSCI/HWCI integration and testing. The planning in each subparagraph shall cover all contractual clauses regarding the identified topic.5.10.1 Preparing for CSCI/HWCI integration and testing5.10.2 Performing CSCI/HWCI integration and testing5.10.3 Revision and retesting5.10.4 Analyzing and recording CSCI/HWCI integration and test results
RATIONALE: Converted from SDP.html heading.

[REQUIREMENT]
UID: REQ-226
STATUS: Draft
TITLE: 5.11 System qualification testing.
STATEMENT: This paragraph shall be divided into the following subparagraphs to describe the approach to be followed for participating in system qualification testing. The planning in each subparagraph shall cover all contractual clauses regarding the identified topic.5.11.1 Independence in system qualification testing5.11.2 Testing on the target computer system5.11.3 Preparing for system qualification testing5.11.4 Dry run of system qualification testing5.11.5 Performing system qualification testing5.11...
RATIONALE: Converted from SDP.html heading.

[REQUIREMENT]
UID: REQ-227
STATUS: Draft
TITLE: 5.12 Preparing for software use.
STATEMENT: This paragraph shall be divided into the following subparagraphs to describe the approach to be followed for preparing for software use. The planning in each subparagraph shall cover all contractual clauses regarding the identified topic.5.12.1 Preparing the executable software5.12.2 Preparing version descriptions for user sites5.12.3 Preparing user manuals5.12.4 Installation at user sites
RATIONALE: Converted from SDP.html heading.

[REQUIREMENT]
UID: REQ-228
STATUS: Draft
TITLE: 5.13 Preparing for software transition.
STATEMENT: This paragraph shall be divided into the following subparagraphs to describe the approach to be followed for preparing for software transition. The planning in each subparagraph shall cover all contractual clauses regarding the identified topic.5.13.1 Preparing the executable software5.13.2 Preparing source files5.13.3 Preparing version descriptions for the support site5.13.4 Preparing the "as built" CSCI design and other software support information5.13.5 Updating the system design descripti...
RATIONALE: Converted from SDP.html heading.

[REQUIREMENT]
UID: REQ-229
STATUS: Draft
TITLE: 5.14 Software configuration management.
STATEMENT: This paragraph shall be divided into the following subparagraphs to describe the approach to be followed for software configuration management. The planning in each subparagraph shall cover all contractual clauses regarding the identified topic.5.14.1 Configuration identification5.14.2 Configuration control5.14.3 Configuration status accounting5.14.4 Configuration audits5.14.5 Packaging, storage, handling, and delivery
RATIONALE: Converted from SDP.html heading.

[REQUIREMENT]
UID: REQ-230
STATUS: Draft
TITLE: 5.15 Software product evaluation.
STATEMENT: This paragraph shall be divided into the following subparagraphs to describe the approach to be followed for software product evaluation. The planning in each subparagraph shall cover all contractual clauses regarding the identified topic.5.15.1 Inprocess and final software product evaluations5.15.2 Software product evaluation records, including items to be recorded5.15.3 Independence in software product evaluation
RATIONALE: Converted from SDP.html heading.

[REQUIREMENT]
UID: REQ-231
STATUS: Draft
TITLE: 5.16 Software quality assurance.
STATEMENT: This paragraph shall be divided into the following subparagraphs to describe the approach to be followed for software quality assurance. The planning in each subparagraph shall cover all contractual clauses regarding the identified topic.5.16.1 Software quality assurance evaluations5.16.2 Software quality assurance records, including items to be recorded5.16.3 Independence in software quality assurance
RATIONALE: Converted from SDP.html heading.

[REQUIREMENT]
UID: REQ-232
STATUS: Draft
TITLE: 5.17 Corrective action.
STATEMENT: This paragraph shall be divided into the following subparagraphs to describe the approach to be followed for corrective action. The planning in each subparagraph shall cover all contractual clauses regarding the identified topic.5.17.1 Problem/change reports, including items to be recorded (candidate items include project name, originator, problem number, problem name, software element or document affected, origination date, category and priority, description, analyst assigned to the problem,...
RATIONALE: Converted from SDP.html heading.

[REQUIREMENT]
UID: REQ-233
STATUS: Draft
TITLE: 5.18 Joint technical and management reviews.
STATEMENT: This paragraph shall be divided into the following subparagraphs to describe the approach to be followed for joint technical and management reviews. The planning in each subparagraph shall cover all contractual clauses regarding the identified topic.5.18.1 Joint technical reviews, including a proposed set of reviews5.18.2 Joint management reviews, including a proposed set of reviews
RATIONALE: Converted from SDP.html heading.

[REQUIREMENT]
UID: REQ-234
STATUS: Draft
TITLE: 5.19 Other software development activities.
STATEMENT: This paragraph shall be divided into the following subparagraphs to describe the approach to be followed for other software development activities. The planning in each subparagraph shall cover all contractual clauses regarding the identified topic.5.19.1 Risk management, including known risks and corresponding strategies5.19.2 Software management indicators, including indicators to be used5.19.3 Security and privacy5.19.4 Subcontractor management5.19.5 Interface with software independent ver...
RATIONALE: Converted from SDP.html heading.

[REQUIREMENT]
UID: REQ-235
STATUS: Draft
TITLE: 6. Schedules and activity network.
STATEMENT: This section shall present:Schedule(s) identifying the activities in each build and showing initiation of each activity, availability of draft and final deliverables and other milestones, and completion of each activityAn activity network, depicting sequential relationships and dependencies among activities and identifying those activities that impose the greatest time restrictions on the project
RATIONALE: Converted from SDP.html heading.

[REQUIREMENT]
UID: REQ-236
STATUS: Draft
TITLE: 7. Project organization and resources.
STATEMENT: This section shall be divided into the following paragraphs to describe the project organization and resources to be applied in each build.
RATIONALE: Converted from SDP.html heading.

[REQUIREMENT]
UID: REQ-237
STATUS: Draft
TITLE: 7.1 Project organization.
STATEMENT: This paragraph shall describe the organizational structure to be used on the project, including the organizations involved, their relationships to one another, and the authority and responsibility of each organization for carrying out required activities.
RATIONALE: Converted from SDP.html heading.

[REQUIREMENT]
UID: REQ-238
STATUS: Draft
TITLE: 7.2 Project resources.
STATEMENT: This paragraph shall describe the resources to be applied to the project. It shall include, as applicable:Personnel resources, including:The estimated staffloading for the project (number of personnel over time)The breakdown of the staffloading numbers by responsibility (for example, management, software engineering, software testing, software configuration management, software product evaluation, software quality assurance)A breakdown of the skill levels, geographic locations, and security c...
RATIONALE: Converted from SDP.html heading.

[REQUIREMENT]
UID: REQ-239
STATUS: Draft
TITLE: 8. Notes.
STATEMENT: This section shall contain any general information that aids in understanding this document (e.g., background information, glossary, rationale). This section shall include an alphabetical listing of all acronyms, abbreviations, and their meanings as used in this document and a list of any terms and definitions needed to understand this document.
RATIONALE: Converted from SDP.html heading.

[REQUIREMENT]
UID: REQ-240
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SDP.html heading.
