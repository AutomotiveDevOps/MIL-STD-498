[DOCUMENT]
TITLE: STR

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-370
STATUS: Draft
TITLE: 1. Scope.
STATEMENT: This section shall be divided into the following paragraphs.
RATIONALE: Converted from STR.html heading.

[REQUIREMENT]
UID: REQ-371
STATUS: Draft
TITLE: 1.1 Identification.
STATEMENT: This paragraph shall contain a full identification of the system and the software to which this document applies, including, as applicable, identification number(s), title(s), abbreviation(s), version number(s), and release number(s).
RATIONALE: Converted from STR.html heading.

[REQUIREMENT]
UID: REQ-372
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from STR.html heading.

[REQUIREMENT]
UID: REQ-373
STATUS: Draft
TITLE: 1.3 Document overview.
STATEMENT: This paragraph shall summarize the purpose and contents of this document and shall describe any security or privacy considerations associated with its use.
RATIONALE: Converted from STR.html heading.

[REQUIREMENT]
UID: REQ-374
STATUS: Draft
TITLE: 2. Referenced documents.
STATEMENT: This section shall list the number, title, revision, and date of all documents referenced in this report. This section shall also identify the source for all documents not available through normal Government stocking activities.
RATIONALE: Converted from STR.html heading.

[REQUIREMENT]
UID: REQ-375
STATUS: Draft
TITLE: 3. Overview of test results.
STATEMENT: This section shall be divided into the following paragraphs to provide an overview of test results.
RATIONALE: Converted from STR.html heading.

[REQUIREMENT]
UID: REQ-376
STATUS: Draft
TITLE: 3.1 Overall assessment of the software tested.
STATEMENT: This paragraph shall:Provide an overall assessment of the software as demonstrated by the test results in this reportIdentify any remaining deficiencies, limitations, or constraints that were detected by the testing performed. Problem/change reports may be used to provide deficiency information.For each remaining deficiency, limitation, or constraint, describe:Its impact on software and system performance, including identification of requirements not metThe impact on software and system desig...
RATIONALE: Converted from STR.html heading.

[REQUIREMENT]
UID: REQ-377
STATUS: Draft
TITLE: 3.2 Impact of test environment.
STATEMENT: This paragraph shall provide an assessment of the manner in which the test environment may be different from the operational environment and the effect of this difference on the test results.
RATIONALE: Converted from STR.html heading.

[REQUIREMENT]
UID: REQ-378
STATUS: Draft
TITLE: 3.3 Recommended improvements.
STATEMENT: This paragraph shall provide any recommended improvements in the design, operation, or testing of the software tested. A discussion of each recommendation and its impact on the software may be provided. If no recommended improvements are provided, this paragraph shall state "None."
RATIONALE: Converted from STR.html heading.

[REQUIREMENT]
UID: REQ-379
STATUS: Draft
TITLE: 4. Detailed test results.
STATEMENT: This section shall be divided into the following paragraphs to describe the detailed results for each test. Note: The word "test" means a related collection of test cases.
RATIONALE: Converted from STR.html heading.

[REQUIREMENT]
UID: REQ-380
STATUS: Draft
TITLE: 4.x (Projectunique identifier of a test).
STATEMENT: This paragraph shall identify a test by projectunique identifier and shall be divided into the following subparagraphs to describe the test results.
RATIONALE: Converted from STR.html heading.

[REQUIREMENT]
UID: REQ-381
STATUS: Draft
TITLE: 4.x.1 Summary of test results.
STATEMENT: This paragraph shall summarize the results of the test. The summary shall include, possibly in a table, the completion status of each test case associated with the test (for example, "all results as expected," "problems encountered," "deviations required"). When the completion status is not "as expected," this paragraph shall reference the following paragraphs for details.
RATIONALE: Converted from STR.html heading.

[REQUIREMENT]
UID: REQ-382
STATUS: Draft
TITLE: 4.x.2 Problems encountered.
STATEMENT: This paragraph shall be divided into subparagraphs that identify each test case in which one or more problems occurred.
RATIONALE: Converted from STR.html heading.

[REQUIREMENT]
UID: REQ-383
STATUS: Draft
TITLE: 4.x.2.y (Projectunique identifier of a test case).
STATEMENT: This paragraph shall identify by projectunique identifier a test case in which one or more problems occurred, and shall provide:A brief description of the problem(s) that occurredIdentification of the test procedure step(s) in which they occurredReference(s) to the associated problem/change report(s) and backup data, as applicableThe number of times the procedure or step was repeated in attempting to correct the problem(s) and the outcome of each attemptBack up points or test steps where test...
RATIONALE: Converted from STR.html heading.

[REQUIREMENT]
UID: REQ-384
STATUS: Draft
TITLE: 4.x.3 Deviations from test cases/procedures.
STATEMENT: This paragraph shall be divided into subparagraphs that identify each test case in which deviations from test case/test procedures occurred.
RATIONALE: Converted from STR.html heading.

[REQUIREMENT]
UID: REQ-385
STATUS: Draft
TITLE: 4.x.3.y (Projectunique identifier of a test case).
STATEMENT: This paragraph shall identify by projectunique identifier a test case in which one or more deviations occurred, and shall provide:A description of the deviation(s) (for example, test case run in which the deviation occurred and nature of the deviation, such as substitution of required equipment, procedural steps not followed, schedule deviations). (Redlined test procedures may be used to show the deviations)The rationale for the deviation(s)An assessment of the deviations' impact on the valid...
RATIONALE: Converted from STR.html heading.

[REQUIREMENT]
UID: REQ-386
STATUS: Draft
TITLE: 5. Test log.
STATEMENT: This section shall present, possibly in a figure or appendix, a chronological record of the test events covered by this report. This test log shall include:The date(s), time(s), and location(s) of the tests performedThe hardware and software configurations used for each test including, as applicable, part/model/serial number, manufacturer, revision level, and calibration date of all hardware, and version number and name for the software components usedThe date and time of each test related ac...
RATIONALE: Converted from STR.html heading.

[REQUIREMENT]
UID: REQ-387
STATUS: Draft
TITLE: 6. Notes.
STATEMENT: This section shall contain any general information that aids in understanding this document (e.g., background information, glossary, rationale). This section shall include an alphabetical listing of all acronyms, abbreviations, and their meanings as used in this document and a list of any terms and definitions needed to understand this document.
RATIONALE: Converted from STR.html heading.

[REQUIREMENT]
UID: REQ-388
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from STR.html heading.
