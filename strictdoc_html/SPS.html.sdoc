[DOCUMENT]
TITLE: SPS

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-045
STATUS: Draft
TITLE: 1. Scope.
STATEMENT: This section shall be divided into the following paragraphs.
RATIONALE: Converted from SPS.html heading.

[REQUIREMENT]
UID: REQ-046
STATUS: Draft
TITLE: 1.1 Identification.
STATEMENT: This paragraph shall contain a full identification of the system and the software to which this document applies, including, as applicable, identification number(s), title(s), abbreviation(s), version number(s), and release number(s).
RATIONALE: Converted from SPS.html heading.

[REQUIREMENT]
UID: REQ-047
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from SPS.html heading.

[REQUIREMENT]
UID: REQ-048
STATUS: Draft
TITLE: 1.3 Document overview.
STATEMENT: This paragraph shall summarize the purpose and contents of this document and shall describe any security or privacy considerations associated with its use.
RATIONALE: Converted from SPS.html heading.

[REQUIREMENT]
UID: REQ-049
STATUS: Draft
TITLE: 2. Referenced documents.
STATEMENT: This section shall list the number, title, revision, and date of all documents referenced in this specification. This section shall also identify the source for all documents not available through normal Government stocking activities.
RATIONALE: Converted from SPS.html heading.

[REQUIREMENT]
UID: REQ-050
STATUS: Draft
TITLE: 3. Requirements.
STATEMENT: This section shall be divided into the following paragraphs to achieve delivery of the software and to establish the requirements that another body of software must meet to be considered a valid copy of the CSCI.Note: In past versions of this DID, Section 3 required a presentation of the software design describing the "as built" software. That approach was modeled on hardware development, in which the product specification presents the final design as the requirement to which hardware items m...
RATIONALE: Converted from SPS.html heading.

[REQUIREMENT]
UID: REQ-051
STATUS: Draft
TITLE: 3.1 Executable software.
STATEMENT: This paragraph shall provide, by reference to enclosed or otherwise provided electronic media, the executable software for the CSCI, including any batch files, command files, data files, or other software files needed to install and operate the software on its target computer(s). In order for a body of software to be considered a valid copy of the CSCI's executable software, it must be shown to match these files exactly.
RATIONALE: Converted from SPS.html heading.

[REQUIREMENT]
UID: REQ-052
STATUS: Draft
TITLE: 3.2 Source files.
STATEMENT: This paragraph shall provide, by reference to enclosed or otherwise provided electronic media, the source files for the CSCI, including any batch files, command files, data files, or other files needed to regenerate the executable software for the CSCI. In order for a body of software to be considered a valid copy of the CSCI's source files, it must be shown to match these files exactly.
RATIONALE: Converted from SPS.html heading.

[REQUIREMENT]
UID: REQ-053
STATUS: Draft
TITLE: 3.3 Packaging requirements.
STATEMENT: This paragraph shall state the requirements, if any, for packaging and marking copies of the CSCI.
RATIONALE: Converted from SPS.html heading.

[REQUIREMENT]
UID: REQ-054
STATUS: Draft
TITLE: 4. Qualification provisions.
STATEMENT: This paragraph shall state the method(s) to be used to demonstrate that a given body of software is a valid copy of the CSCI. For example, the method for executable files might be to establish that each executable file referenced in 3.1 has an identicallynamed counterpart in the software in question and that each such counterpart can be shown, via bitforbit comparison, check sum, or other method, to be identical to the corresponding executable file. The method for source files might be compar...
RATIONALE: Converted from SPS.html heading.

[REQUIREMENT]
UID: REQ-055
STATUS: Draft
TITLE: 5. Software support information.
STATEMENT: This section shall be divided into the following paragraphs to provide information needed to support the CSCI.
RATIONALE: Converted from SPS.html heading.

[REQUIREMENT]
UID: REQ-056
STATUS: Draft
TITLE: 5.1 "As built" software design.
STATEMENT: This paragraph shall contain, or reference an appendix or other deliverable document that contains, information describing the design of the "as built" CSCI. The information shall be the same as that required in a Software Design Description (SDD), Interface Design Description (IDD), and Database Design Description (DBDD), as applicable. If these documents or their equivalents are to be delivered for the "as built" CSCI, this paragraph shall reference them. If not, the information shall be pr...
RATIONALE: Converted from SPS.html heading.

[REQUIREMENT]
UID: REQ-057
STATUS: Draft
TITLE: 5.2 Compilation/build procedures.
STATEMENT: This paragraph shall describe, or reference an appendix that describes, the compilation/build process to be used to create the executable files from the source files and to prepare the executable files to be loaded into firmware or other distribution media. It shall specify the compiler(s)/assembler(s) to be used, including version numbers; other hardware and software needed, including version numbers; any settings, options, or conventions to be used; and procedures for compiling/assembling, ...
RATIONALE: Converted from SPS.html heading.

[REQUIREMENT]
UID: REQ-058
STATUS: Draft
TITLE: 5.3 Modification procedures.
STATEMENT: This paragraph shall describe procedures that must be followed to modify the CSCI. It shall include or reference information on the following, as applicable:Support facilities, equipment, and software, and procedures for their useDatabases/data files used by the CSCI and procedures for using and modifying themDesign, coding, and other conventions to be followedCompilation/build procedures if different from those aboveIntegration and testing procedures to be followed
RATIONALE: Converted from SPS.html heading.

[REQUIREMENT]
UID: REQ-059
STATUS: Draft
TITLE: 5.4 Computer hardware resource utilization.
STATEMENT: This paragraph shall describe the "as built" CSCI's measured utilization of computer hardware resources (such as processor capacity, memory capacity, input/output device capacity, auxiliary storage capacity, and communications/ network equipment capacity). It shall cover all computer hardware resources included in utilization requirements for the CSCI, in systemlevel resource allocations affecting the CSCI, or in the software development plan. If all utilization data for a given computer hard...
RATIONALE: Converted from SPS.html heading.

[REQUIREMENT]
UID: REQ-060
STATUS: Draft
TITLE: 6. Requirements traceability.
STATEMENT: This section shall provide:Traceability from each CSCI source file to the software unit(s) that it implements.Traceability from each software unit to the source files that implement it.Traceability from each computer hardware resource utilization measurement given in 5.4 to the CSCI requirements it addresses. (Alternatively, this traceability may be provided in 5.4.)Traceability from each CSCI requirement regarding computer hardware resource utilization to the utilization measurements given i...
RATIONALE: Converted from SPS.html heading.

[REQUIREMENT]
UID: REQ-061
STATUS: Draft
TITLE: 7. Notes.
STATEMENT: This section shall contain any general information that aids in understanding this specification (e.g., background information, glossary, rationale). This section shall include an alphabetical listing of all acronyms, abbreviations, and their meanings as used in this document and a list of any terms and definitions needed to understand this document.
RATIONALE: Converted from SPS.html heading.

[REQUIREMENT]
UID: REQ-062
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SPS.html heading.
