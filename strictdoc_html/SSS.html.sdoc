[DOCUMENT]
TITLE: SSS

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-160
STATUS: Draft
TITLE: 1. Scope.
STATEMENT: This section shall be divided into the following paragraphs.
RATIONALE: Converted from SSS.html heading.

[REQUIREMENT]
UID: REQ-161
STATUS: Draft
TITLE: 1.1 Identification.
STATEMENT: This paragraph shall contain a full identification of the system to which this document applies, including, as applicable, identification number(s), title(s), abbreviation(s), version number(s), and release number(s).
RATIONALE: Converted from SSS.html heading.

[REQUIREMENT]
UID: REQ-162
STATUS: Draft
TITLE: 1.2 System overview.
STATEMENT: This paragraph shall briefly state the purpose of the system to which this document applies. It shall describe the general nature of the system; summarize the history of system development, operation, and maintenance; identify the project sponsor, acquirer, user, developer, and support agencies; identify current and planned operating sites; and list other relevant documents.
RATIONALE: Converted from SSS.html heading.

[REQUIREMENT]
UID: REQ-163
STATUS: Draft
TITLE: 1.3 Document overview.
STATEMENT: This paragraph shall summarize the purpose and contents of this document and shall describe any security or privacy considerations associated with its use.
RATIONALE: Converted from SSS.html heading.

[REQUIREMENT]
UID: REQ-164
STATUS: Draft
TITLE: 2. Referenced documents.
STATEMENT: This section shall list the number, title, revision, and date of all documents referenced in this specification. This section shall also identify the source for all documents not available through normal Government stocking activities.
RATIONALE: Converted from SSS.html heading.

[REQUIREMENT]
UID: REQ-165
STATUS: Draft
TITLE: 3. Requirements.
STATEMENT: This section shall be divided into the following paragraphs to specify the system requirements, that is, those characteristics of the system that are conditions for its acceptance. Each requirement shall be assigned a projectunique identifier to support testing and traceability and shall be stated in such a way that an objective test can be defined for it. Each requirement shall be annotated with associated qualification method(s) (see section 4) and, for subsystems, traceability to system re...
RATIONALE: Converted from SSS.html heading.

[REQUIREMENT]
UID: REQ-166
STATUS: Draft
TITLE: 3.1 Required states and modes.
STATEMENT: If the system is required to operate in more than one state or mode having requirements distinct from other states or modes, this paragraph shall identify and define each state and mode. Examples of states and modes include: idle, ready, active, postuse analysis, training, degraded, emergency, backup, wartime, peacetime. The distinction between states and modes is arbitrary. A system may be described in terms of states only, modes only, states within modes, modes within states, or any other s...
RATIONALE: Converted from SSS.html heading.

[REQUIREMENT]
UID: REQ-167
STATUS: Draft
TITLE: 3.2 System capability requirements.
STATEMENT: This paragraph shall be divided into subparagraphs to itemize the requirements associated with each capability of the system. A "capability" is defined as a group of related requirements. The word "capability" may be replaced with "function," "subject," "object," or other term useful for presenting the requirements.
RATIONALE: Converted from SSS.html heading.

[REQUIREMENT]
UID: REQ-168
STATUS: Draft
TITLE: 3.2.x (System capability).
STATEMENT: This paragraph shall identify a required system capability and shall itemize the requirements associated with the capability. If the capability can be more clearly specified by dividing it into constituent capabilities, the constituent capabilities shall be specified in subparagraphs. The requirements shall specify required behavior of the system and shall include applicable parameters, such as response times, throughput times, other timing constraints, sequencing, accuracy, capacities (how m...
RATIONALE: Converted from SSS.html heading.

[REQUIREMENT]
UID: REQ-169
STATUS: Draft
TITLE: 3.3 System external interface requirements.
STATEMENT: This paragraph shall be divided into subparagraphs to specify the requirements, if any, for the system's external interfaces. This paragraph may reference one or more Interface Requirements Specifications (IRSs) or other documents containing these requirements.
RATIONALE: Converted from SSS.html heading.

[REQUIREMENT]
UID: REQ-170
STATUS: Draft
TITLE: 3.3.1 Interface identification and diagrams.
STATEMENT: This paragraph shall identify the required external interfaces of the system. The identification of each interface shall include a projectunique identifier and shall designate the interfacing entities (systems, configuration items, users, etc.) by name, number, version, and documentation references, as applicable. The identification shall state which entities have fixed interface characteristics (and therefore impose interface requirements on interfacing entities) and which are being develope...
RATIONALE: Converted from SSS.html heading.

[REQUIREMENT]
UID: REQ-171
STATUS: Draft
TITLE: 3.3.x (Project unique identifier of interface).
STATEMENT: This paragraph (beginning with 3.3.2) shall identify a system external interface by project unique identifier, shall briefly identify the interfacing entities, and shall be divided into subparagraphs as needed to state the requirements imposed on the system to achieve the interface. Interface characteristics of the other entities involved in the interface shall be stated as assumptions or as "When [the entity not covered] does this, the system shall...," not as requirements on the other entit...
RATIONALE: Converted from SSS.html heading.

[REQUIREMENT]
UID: REQ-172
STATUS: Draft
TITLE: 3.4 System internal interface requirements.
STATEMENT: This paragraph shall specify the requirements, if any, imposed on interfaces internal to the system. If all internal interfaces are left to the design or to requirement specifications for system components, this fact shall be so stated. If such requirements are to be imposed, paragraph 3.3 of this DID provides a list of topics to be considered.
RATIONALE: Converted from SSS.html heading.

[REQUIREMENT]
UID: REQ-173
STATUS: Draft
TITLE: 3.5 System internal data requirements.
STATEMENT: This paragraph shall specify the requirements, if any, imposed on data internal to the system. Included shall be requirements, if any, on databases and data files to be included in the system. If all decisions about internal data are left to the design or to requirements specifications for system components, this fact shall be so stated. If such requirements are to be imposed, paragraphs 3.3.x.c and 3.3.x.d of this DID provide a list of topics to be considered.
RATIONALE: Converted from SSS.html heading.

[REQUIREMENT]
UID: REQ-174
STATUS: Draft
TITLE: 3.6 Adaptation requirements.
STATEMENT: This paragraph shall specify the requirements, if any, concerning installationdependent data that the system is required to provide (such as sitedependent latitude and longitude or sitedependent state tax codes) and operational parameters that the system is required to use that may vary according to operational needs (such as parameters indicating operationdependent targeting constants or data recording).
RATIONALE: Converted from SSS.html heading.

[REQUIREMENT]
UID: REQ-175
STATUS: Draft
TITLE: 3.7 Safety requirements.
STATEMENT: This paragraph shall specify the system requirements, if any, concerned with preventing or minimizing unintended hazards to personnel, property, and the physical environment. Examples include restricting the use of dangerous materials; classifying explosives for purposes of shipping, handling, and storing; abort/escape provisions from enclosures; gas detection and warning devices; grounding of electrical systems; decontamination; and explosion proofing. This paragraph shall include the system...
RATIONALE: Converted from SSS.html heading.

[REQUIREMENT]
UID: REQ-176
STATUS: Draft
TITLE: 3.8 Security and privacy requirements.
STATEMENT: This paragraph shall specify the system requirements, if any, concerned with maintaining security and privacy. The requirements shall include, as applicable, the security/privacy environment in which the system must operate, the type and degree of security or privacy to be provided, the security/privacy risks the system must withstand, required safeguards to reduce those risks, the security/privacy policy that must be met, the security/privacy accountability the system must provide, and the c...
RATIONALE: Converted from SSS.html heading.

[REQUIREMENT]
UID: REQ-177
STATUS: Draft
TITLE: 3.9 System environment requirements.
STATEMENT: This paragraph shall specify the system requirements, if any, concerned with maintaining security and privacy. The requirements shall include, as applicable, the security/privacy environment in which the system must operate, the type and degree of security or privacy to be provided, the security/privacy risks the system must withstand, required safeguards to reduce those risks, the security/privacy policy that must be met, the security/privacy accountability the system must provide, and the c...
RATIONALE: Converted from SSS.html heading.

[REQUIREMENT]
UID: REQ-178
STATUS: Draft
TITLE: 3.9 System environment requirements.
STATEMENT: This paragraph shall specify the requirements, if any, regarding the environment in which the system must operate. Examples for a software system are the computer hardware and operating system on which the software must run. (Additional requirements concerning computer resources are given in the next paragraph). Examples for a hardwaresoftware system include the environmental conditions that the system must withstand during transportation, storage, and operation, such as conditions in the nat...
RATIONALE: Converted from SSS.html heading.

[REQUIREMENT]
UID: REQ-179
STATUS: Draft
TITLE: 3.10 Computer resource requirements.
STATEMENT: This paragraph shall be divided into the following subparagraphs. Depending upon the nature of the system, the computer resources covered in these subparagraphs may constitute the environment of the system (as for a software system) or components of the system (as for a hardwaresoftware system).
RATIONALE: Converted from SSS.html heading.

[REQUIREMENT]
UID: REQ-180
STATUS: Draft
TITLE: 3.10.1 Computer hardware requirements.
STATEMENT: This paragraph shall specify the requirements, if any, regarding computer hardware that must be used by, or incorporated into, the system. The requirements shall include, as applicable, number of each type of equipment, type, size, capacity, and other required characteristics of processors, memory, input/output devices, auxiliary storage, communications/network equipment, and other required equipment.
RATIONALE: Converted from SSS.html heading.

[REQUIREMENT]
UID: REQ-181
STATUS: Draft
TITLE: 3.10.2 Computer hardware resource utilization requirements.
STATEMENT: This paragraph shall specify the requirements, if any, on the system's computer hardware resource utilization, such as maximum allowable use of processor capacity, memory capacity, input/output device capacity, auxiliary storage device capacity, and communications/network equipment capacity. The requirements (stated, for example, as percentages of the capacity of each computer hardware resource) shall include the conditions, if any, under which the resource utilization is to be measured.
RATIONALE: Converted from SSS.html heading.

[REQUIREMENT]
UID: REQ-182
STATUS: Draft
TITLE: 3.10.3 Computer software requirements.
STATEMENT: This paragraph shall specify the requirements, if any, regarding computer software that must be used by, or incorporated into, the system. Examples include operating systems, database management systems, communications/ network software, utility software, input and equipment simulators, test software, and manufacturing software. The correct nomenclature, version, and documentation references of each such software item shall be provided.
RATIONALE: Converted from SSS.html heading.

[REQUIREMENT]
UID: REQ-183
STATUS: Draft
TITLE: 3.10.4 Computer communications requirements.
STATEMENT: This paragraph shall specify the additional requirements, if any, concerning the computer communications that must be used by, or incorporated into, the system. Examples include geographic locations to be linked; configuration and network topology; transmission techniques; data transfer rates; gateways; required system use times; type and volume of data to be transmitted/received; time boundaries for transmission/reception/response; peak volumes of data; and diagnostic features.
RATIONALE: Converted from SSS.html heading.

[REQUIREMENT]
UID: REQ-184
STATUS: Draft
TITLE: 3.11 System quality factors.
STATEMENT: This paragraph shall specify the requirements, if any, pertaining to system quality factors. Examples include quantitative requirements concerning system functionality (the ability to perform all required functions), reliability (the ability to perform with correct, consistent results such as mean time between failure for equipment), maintainability (the ability to be easily serviced, repaired, or corrected), availability (the ability to be accessed and operated when needed), flexibility (the...
RATIONALE: Converted from SSS.html heading.

[REQUIREMENT]
UID: REQ-185
STATUS: Draft
TITLE: 3.12 Design and construction constraints.
STATEMENT: This paragraph shall specify the requirements, if any, that constrain the design and construction of the system. For hardwaresoftware systems, this paragraph shall include the physical requirements imposed on the system. These requirements may be specified by reference to appropriate commercial or military standards and specifications. Examples include requirements concerning:Use of a particular system architecture or requirements on the architecture, such as required subsystems; use of stand...
RATIONALE: Converted from SSS.html heading.

[REQUIREMENT]
UID: REQ-186
STATUS: Draft
TITLE: 3.13 Personnelrelated requirements.
STATEMENT: This paragraph shall specify the system requirements, if any, included to accommodate the number, skill levels, duty cycles, training needs, or other information about the personnel who will use or support the system. Examples include requirements for the number of work stations to be provided and for builtin help and training features. Also included shall be the human factors engineering requirements, if any, imposed on the system. These requirements shall include, as applicable, considerati...
RATIONALE: Converted from SSS.html heading.

[REQUIREMENT]
UID: REQ-187
STATUS: Draft
TITLE: 3.14 Trainingrelated requirements.
STATEMENT: This paragraph shall specify the system requirements, if any, pertaining to training. Examples include training devices and training materials to be included in the system.
RATIONALE: Converted from SSS.html heading.

[REQUIREMENT]
UID: REQ-188
STATUS: Draft
TITLE: 3.15 Logisticsrelated requirements.
STATEMENT: This paragraph shall specify the system requirements, if any, concerned with logistics considerations. These considerations may include: system maintenance, software support, system transportation modes, supply system requirements, impact on existing facilities, and impact on existing equipment.
RATIONALE: Converted from SSS.html heading.

[REQUIREMENT]
UID: REQ-189
STATUS: Draft
TITLE: 3.16 Other requirements.
STATEMENT: This paragraph shall specify additional system requirements, if any, not covered in the previous paragraphs. Examples include requirements for system documentation, such as specifications, drawings, technical manuals, test plans and procedures, and installation instruction data, if not covered in other contractual documents.
RATIONALE: Converted from SSS.html heading.

[REQUIREMENT]
UID: REQ-190
STATUS: Draft
TITLE: 3.17 Packaging requirements.
STATEMENT: This section shall specify the requirements, if any, for packaging, labeling, and handling the system and its components for delivery. Applicable military specifications and standards may be referenced if appropriate.
RATIONALE: Converted from SSS.html heading.

[REQUIREMENT]
UID: REQ-191
STATUS: Draft
TITLE: 3.18 Precedence and criticality of requirements.
STATEMENT: This paragraph shall specify, if applicable, the order of precedence, criticality, or assigned weights indicating the relative importance of the requirements in this specification. Examples include identifying those requirements deemed critical to safety, to security, or to privacy for purposes of singling them out for special treatment. If all requirements have equal weight, this paragraph shall so state.
RATIONALE: Converted from SSS.html heading.

[REQUIREMENT]
UID: REQ-192
STATUS: Draft
TITLE: 4. Qualification provisions.
STATEMENT: This section shall define a set of qualification methods and shall specify for each requirement in Section 3 the method(s) to be used to ensure that the requirement has been met. A table may be used to present this information, or each requirement in Section 3 may be annotated with the method(s) to be used. Qualification methods may include:Demonstration: The operation of the system, or a part of the system, that relies on observable functional operation not requiring the use of instrumentati...
RATIONALE: Converted from SSS.html heading.

[REQUIREMENT]
UID: REQ-193
STATUS: Draft
TITLE: 5. Requirements traceability.
STATEMENT: For systemlevel specifications, this paragraph does not apply. For subsystemlevel specifications, this paragraph shall contain:Traceability from each subsystem requirement in this specification to the system requirements it addresses. (Alternatively, this traceability may be provided by annotating each requirement in Section 3.)Note: Each level of system refinement may result in requirements not directly traceable to higherlevel requirements. For example, a system architectural design that cr...
RATIONALE: Converted from SSS.html heading.

[REQUIREMENT]
UID: REQ-194
STATUS: Draft
TITLE: 6. Notes.
STATEMENT: This section shall contain any general information that aids in understanding this document (e.g., background information, glossary, rationale). This section shall contain an alphabetical listing of all acronyms, abbreviations, and their meanings as used in this document and a list of any terms and definitions needed to understand this document.
RATIONALE: Converted from SSS.html heading.

[REQUIREMENT]
UID: REQ-195
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SSS.html heading.
