[DOCUMENT]
TITLE: SUM

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-325
STATUS: Draft
TITLE: 1. Scope.
STATEMENT: This section shall be divided into the following paragraphs.
RATIONALE: Converted from SUM.html heading.

[REQUIREMENT]
UID: REQ-326
STATUS: Draft
TITLE: 1.1 Identification.
STATEMENT: This paragraph shall contain a full identification of the system and the software to which this document applies, including, as applicable, identification number(s), title(s), abbreviation(s), version number(s), and release number(s).
RATIONALE: Converted from SUM.html heading.

[REQUIREMENT]
UID: REQ-327
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from SUM.html heading.

[REQUIREMENT]
UID: REQ-328
STATUS: Draft
TITLE: 1.3 Document overview.
STATEMENT: This paragraph shall summarize the purpose and contents of this manual and shall describe any security or privacy considerations associated with its use.
RATIONALE: Converted from SUM.html heading.

[REQUIREMENT]
UID: REQ-329
STATUS: Draft
TITLE: 2. Referenced documents.
STATEMENT: This section shall list the number, title, revision, and date of all documents referenced in this manual. This section shall also identify the source for all documents not available through normal Government stocking activities.
RATIONALE: Converted from SUM.html heading.

[REQUIREMENT]
UID: REQ-330
STATUS: Draft
TITLE: 3. Software summary.
STATEMENT: This section shall be divided into the following paragraphs.
RATIONALE: Converted from SUM.html heading.

[REQUIREMENT]
UID: REQ-331
STATUS: Draft
TITLE: 3.1 Software application.
STATEMENT: This paragraph shall provide a brief description of the intended uses of the software. Capabilities, operating improvements, and benefits expected from its use shall be described.
RATIONALE: Converted from SUM.html heading.

[REQUIREMENT]
UID: REQ-332
STATUS: Draft
TITLE: 3.2 Software inventory.
STATEMENT: This paragraph shall identify all software files, including databases and data files, that must be installed for the software to operate. The identification shall include security and privacy considerations for each file and identification of the software necessary to continue or resume operation in case of an emergency.
RATIONALE: Converted from SUM.html heading.

[REQUIREMENT]
UID: REQ-333
STATUS: Draft
TITLE: 3.3 Software environment.
STATEMENT: This paragraph shall identify the hardware, software, manual operations, and other resources needed for a user to install and run the software. Included, as applicable, shall be identification of:Computer equipment that must be present, including amount of memory needed, amount of auxiliary storage needed, and peripheral equipment such as printers and other input/output devicesCommunications equipment that must be presentOther software that must be present, such as operating systems, database...
RATIONALE: Converted from SUM.html heading.

[REQUIREMENT]
UID: REQ-334
STATUS: Draft
TITLE: 3.4 Software organization and overview of operation.
STATEMENT: This paragraph shall provide a brief description of the organization and operation of the software from the user's point of view. The description shall include, as applicable:Logical components of the software, from the user's point of view, and an overview of the purpose/operation of each componentPerformance characteristics that can be expected by the user, such as:Types, volumes, rate of inputs acceptedTypes, volume, accuracy, rate of outputs that the software can produceTypical response t...
RATIONALE: Converted from SUM.html heading.

[REQUIREMENT]
UID: REQ-335
STATUS: Draft
TITLE: 3.5 Contingencies and alternate states and modes of operation.
STATEMENT: This paragraph shall explain differences in what the user will be able to do with the software at times of emergency and in various states and modes of operation, if applicable.
RATIONALE: Converted from SUM.html heading.

[REQUIREMENT]
UID: REQ-336
STATUS: Draft
TITLE: 3.6 Security and privacy.
STATEMENT: This paragraph shall contain an overview of the security and privacy considerations associated with the software. A warning shall be included regarding making unauthorized copies of software or documents, if applicable.
RATIONALE: Converted from SUM.html heading.

[REQUIREMENT]
UID: REQ-337
STATUS: Draft
TITLE: 3.7 Assistance and problem reporting.
STATEMENT: This paragraph shall identify points of contact and procedures to be followed to obtain assistance and report problems encountered in using the software.
RATIONALE: Converted from SUM.html heading.

[REQUIREMENT]
UID: REQ-338
STATUS: Draft
TITLE: 4. Access to the software.
STATEMENT: This section shall contain stepbystep procedures oriented to the first time/occasional user. Enough detail shall be presented so that the user can reliably access the software before learning the details of its functional capabilities. Safety precautions, marked by WARNING or CAUTION, shall be included where applicable.
RATIONALE: Converted from SUM.html heading.

[REQUIREMENT]
UID: REQ-339
STATUS: Draft
TITLE: 4.1 Firsttime user of the software.
STATEMENT: This paragraph shall be divided into the following subparagraphs.
RATIONALE: Converted from SUM.html heading.

[REQUIREMENT]
UID: REQ-340
STATUS: Draft
TITLE: 4.1.1 Equipment familiarization.
STATEMENT: This paragraph shall describe the following as appropriate:Procedures for turning on power and making adjustmentsDimensions and capabilities of the visual display screenAppearance of the cursor, how to identify an active cursor if more than one cursor can appear, how to position a cursor, and how to use a cursorKeyboard layout and role of different types of keys and pointing devicesProcedures for turning power off if special sequencing of operations is needed
RATIONALE: Converted from SUM.html heading.

[REQUIREMENT]
UID: REQ-341
STATUS: Draft
TITLE: 4.1.2 Access control.
STATEMENT: This paragraph shall present an overview of the access and security features of the software that are visible to the user. The following items shall be included, as applicable:How and from whom to obtain a passwordHow to add, delete, or change passwords under user controlSecurity and privacy considerations pertaining to the storage and marking of output reports and other media that the user will generate
RATIONALE: Converted from SUM.html heading.

[REQUIREMENT]
UID: REQ-342
STATUS: Draft
TITLE: 4.1.3 Installation and setup.
STATEMENT: This paragraph shall describe any procedures that the user must perform to be identified or authorized to access or install software on the equipment, to perform the installation, to configure the software, to delete or overwrite former files or data, and to enter parameters for software operation.
RATIONALE: Converted from SUM.html heading.

[REQUIREMENT]
UID: REQ-343
STATUS: Draft
TITLE: 4.2 Initiating a session.
STATEMENT: This paragraph shall provide stepbystep procedures for beginning work, including any options available. A checklist for problem determination shall be included in case difficulties are encountered.
RATIONALE: Converted from SUM.html heading.

[REQUIREMENT]
UID: REQ-344
STATUS: Draft
TITLE: 4.3 Stopping and suspending work.
STATEMENT: This paragraph shall describe how the user can cease or interrupt use of the software and how to determine whether normal termination or cessation has occurred.
RATIONALE: Converted from SUM.html heading.

[REQUIREMENT]
UID: REQ-345
STATUS: Draft
TITLE: 5. Processing reference guide.
STATEMENT: This section shall provide the user with procedures for using the software. If procedures are complicated or extensive, additional Sections 6, 7, ... may be added in the same paragraph structure as this section and with titles meaningful to the sections selected. The organization of the document will depend on the characteristics of the software being documented. For example, one approach is to base the sections on the organizations in which users work, their assigned positions, their work si...
RATIONALE: Converted from SUM.html heading.

[REQUIREMENT]
UID: REQ-346
STATUS: Draft
TITLE: 5.1 Capabilities.
STATEMENT: This paragraph shall briefly describe the interrelationships of the transactions, menus, functions, or other processes in order to provide an overview of the use of the software.
RATIONALE: Converted from SUM.html heading.

[REQUIREMENT]
UID: REQ-347
STATUS: Draft
TITLE: 5.2 Conventions.
STATEMENT: This paragraph shall describe any conventions used by the software, such as the use of colors in displays, the use of audible alarms, the use of abbreviated vocabulary, and the use of rules for assigning names or codes.
RATIONALE: Converted from SUM.html heading.

[REQUIREMENT]
UID: REQ-348
STATUS: Draft
TITLE: 5.3 Processing procedures.
STATEMENT: This paragraph shall explain the organization of subsequent paragraphs, e.g., by function, by menu, by screen. Any necessary order in which procedures must be accomplished shall be described.
RATIONALE: Converted from SUM.html heading.

[REQUIREMENT]
UID: REQ-349
STATUS: Draft
TITLE: 5.3.x (Aspect of software use).
STATEMENT: The title of this paragraph shall identify the function, menu, transaction, or other process being described. This paragraph shall describe and give options and examples, as applicable, of menus, graphical icons, data entry forms, user inputs, inputs from other software or hardware that may affect the software's interface with the user, outputs, diagnostic or error messages or alarms, and help facilities that can provide online descriptive or tutorial information. The format for presenting th...
RATIONALE: Converted from SUM.html heading.

[REQUIREMENT]
UID: REQ-350
STATUS: Draft
TITLE: 5.4 Related processing.
STATEMENT: This paragraph shall identify and describe any related batch, offline, or background processing performed by the software that is not invoked directly by the user and is not described in paragraph 5.3. Any user responsibilities to support this processing shall be specified.
RATIONALE: Converted from SUM.html heading.

[REQUIREMENT]
UID: REQ-351
STATUS: Draft
TITLE: 5.5 Data backup.
STATEMENT: This paragraph shall describe procedures for creating and retaining backup data that can be used to replace primary copies of data in event of errors, defects, malfunctions, or accidents.
RATIONALE: Converted from SUM.html heading.

[REQUIREMENT]
UID: REQ-352
STATUS: Draft
TITLE: 5.6 Recovery from errors, malfunctions, and emergencies.
STATEMENT: This paragraph shall present detailed procedures for restart or recovery from errors or malfunctions occurring during processing and for ensuring continuity of operations in the event of emergencies.
RATIONALE: Converted from SUM.html heading.

[REQUIREMENT]
UID: REQ-353
STATUS: Draft
TITLE: 5.7 Messages.
STATEMENT: This paragraph shall list, or refer to an appendix that lists, all error messages, diagnostic messages, and information messages that can occur while accomplishing any of the user's functions. The meaning of each message and the action that should be taken after each such message shall be identified and described.
RATIONALE: Converted from SUM.html heading.

[REQUIREMENT]
UID: REQ-354
STATUS: Draft
TITLE: 5.8 Quickreference guide.
STATEMENT: If appropriate to the software, this paragraph shall provide or reference a quickreference card or page for using the software. This quickreference guide shall summarize, as applicable, frequentlyused function keys, control sequences, formats, commands, or other aspects of software use.
RATIONALE: Converted from SUM.html heading.

[REQUIREMENT]
UID: REQ-355
STATUS: Draft
TITLE: 6. Notes.
STATEMENT: This section shall contain any general information that aids in understanding this document (e.g., background information, glossary, rationale). This section shall include an alphabetical listing of all acronyms, abbreviations, and their meanings as used in this document and a list of terms and definitions needed to understand this document. If section 5 has been expanded into section(s) 6, . . ., this section shall be numbered as the next section following section n.
RATIONALE: Converted from SUM.html heading.

[REQUIREMENT]
UID: REQ-356
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SUM.html heading.
