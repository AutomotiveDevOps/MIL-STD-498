[DOCUMENT]
TITLE: SIP

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-281
STATUS: Draft
TITLE: 1. Scope.
STATEMENT: This section shall be divided into the following paragraphs.
RATIONALE: Converted from SIP.html heading.

[REQUIREMENT]
UID: REQ-282
STATUS: Draft
TITLE: 1.1 Identification.
STATEMENT: This paragraph shall contain a full identification of the system and the software to which this document applies, including, as applicable, identification number(s), title(s), abbreviation(s), version number(s), and release number(s).
RATIONALE: Converted from SIP.html heading.

[REQUIREMENT]
UID: REQ-283
STATUS: Draft
TITLE: 1.2 System overview.
STATEMENT: This paragraph shall briefly state the purpose of the system and the software to which this document applies. It shall describe the general nature of the system and software; summarize the history of system development, operation, and maintenance; identify the project sponsor, acquirer, user, developer, and support agencies; identify current and planned operating sites; and list other relevant documents.
RATIONALE: Converted from SIP.html heading.

[REQUIREMENT]
UID: REQ-284
STATUS: Draft
TITLE: 1.3 Document overview.
STATEMENT: This paragraph shall summarize the purpose and contents of this plan and shall describe any security or privacy considerations associated with its use.
RATIONALE: Converted from SIP.html heading.

[REQUIREMENT]
UID: REQ-285
STATUS: Draft
TITLE: 1.4 Relationship to other plans.
STATEMENT: This paragraph shall describe the relationship, if any, of the SIP to other project management plans.
RATIONALE: Converted from SIP.html heading.

[REQUIREMENT]
UID: REQ-286
STATUS: Draft
TITLE: 2. Referenced documents.
STATEMENT: This section shall list the number, title, revision, and date of all documents referenced in this plan. This section shall also identify the source for all documents not available through normal Government stocking activities.
RATIONALE: Converted from SIP.html heading.

[REQUIREMENT]
UID: REQ-287
STATUS: Draft
TITLE: 3. Installation overview.
STATEMENT: This section shall be divided into the following paragraphs to provide an overview of the installation process.
RATIONALE: Converted from SIP.html heading.

[REQUIREMENT]
UID: REQ-288
STATUS: Draft
TITLE: 3.1 Description.
STATEMENT: This paragraph shall provide a general description of the installation process to provide a frame of reference for the remainder of the document. A list of sites for software installation, the schedule dates, and the method of installation shall be included.
RATIONALE: Converted from SIP.html heading.

[REQUIREMENT]
UID: REQ-289
STATUS: Draft
TITLE: 3.2 Contact point.
STATEMENT: This paragraph shall provide the organizational name, office symbol/code, and telephone number of a point of contact for questions relating to this installation.
RATIONALE: Converted from SIP.html heading.

[REQUIREMENT]
UID: REQ-290
STATUS: Draft
TITLE: 3.3 Support materials.
STATEMENT: This paragraph shall list the type, source, and quantity of support materials needed for the installation. Included shall be items such as magnetic tapes, disk packs, computer printer paper, and special forms.
RATIONALE: Converted from SIP.html heading.

[REQUIREMENT]
UID: REQ-291
STATUS: Draft
TITLE: 3.4 Training.
STATEMENT: This paragraph shall describe the developer's plans for training personnel who will operate and/or use the software installed at user sites. Included shall be the delineation between general orientation, classroom training, and "hands on" training.
RATIONALE: Converted from SIP.html heading.

[REQUIREMENT]
UID: REQ-292
STATUS: Draft
TITLE: 3.5 Tasks.
STATEMENT: This paragraph shall list and describe in general terms each task involved in the software installation. Each task description shall identify the organization that will accomplish the task, usually either the user, computer operations, or the developer. The task list shall include such items as:Providing overall planning, coordination, and preparation for installationProviding personnel for the installation teamArranging lodging, transportation, and office facilities for the installation team...
RATIONALE: Converted from SIP.html heading.

[REQUIREMENT]
UID: REQ-293
STATUS: Draft
TITLE: 3.6 Personnel.
STATEMENT: This paragraph shall describe the number, type, and skill level of the personnel needed during the installation period, including the need for multishift operation, clerical support, etc.
RATIONALE: Converted from SIP.html heading.

[REQUIREMENT]
UID: REQ-294
STATUS: Draft
TITLE: 3.7 Security and privacy.
STATEMENT: This paragraph shall contain an overview of the security and privacy considerations associated with the system.
RATIONALE: Converted from SIP.html heading.

[REQUIREMENT]
UID: REQ-295
STATUS: Draft
TITLE: 4. Sitespecific information for software center operations staff.
STATEMENT: This section applies if the software will be installed in computer center(s) or other centralized or networked software installations for users to access via terminals or using batch inputs/outputs. If this type of installation does not apply, this section shall contain the words "Not applicable."
RATIONALE: Converted from SIP.html heading.

[REQUIREMENT]
UID: REQ-296
STATUS: Draft
TITLE: 4.x (Site name).
STATEMENT: This paragraph shall identify a site or set of sites and shall be divided into the following subparagraphs to discuss those sites. Multiple sites may be discussed together when the information for those sites is generally the same.
RATIONALE: Converted from SIP.html heading.

[REQUIREMENT]
UID: REQ-297
STATUS: Draft
TITLE: 4.x.1 Schedule.
STATEMENT: This paragraph shall present a schedule of tasks to be accomplished during installation. It shall depict the tasks in chronological order with beginning and ending dates of each task and supporting narrative as necessary.
RATIONALE: Converted from SIP.html heading.

[REQUIREMENT]
UID: REQ-298
STATUS: Draft
TITLE: 4.x.2 Software inventory.
STATEMENT: This paragraph shall provide an inventory of the software needed to support the installation. The software shall be identified by name, identification number, version number, release number, configuration, and security classification, as applicable. This paragraph shall indicate whether the software is expected to be on site or will be delivered for the installation and shall identify any software to be used only to facilitate the installation process.
RATIONALE: Converted from SIP.html heading.

[REQUIREMENT]
UID: REQ-299
STATUS: Draft
TITLE: 4.x.3 Facilities.
STATEMENT: This paragraph shall detail the physical facilities and accommodations needed during the installation period. This description shall include the following, as applicable:Classroom, work space, and training aids needed, specifying hours per day, number of days, and shiftsHardware that must be operational and availableTransportation and lodging for the installation team
RATIONALE: Converted from SIP.html heading.

[REQUIREMENT]
UID: REQ-300
STATUS: Draft
TITLE: 4.x.4 Installation team.
STATEMENT: This paragraph shall describe the composition of the installation team. Each team member's tasks shall be defined.
RATIONALE: Converted from SIP.html heading.

[REQUIREMENT]
UID: REQ-301
STATUS: Draft
TITLE: 4.x.5 Installation procedures.
STATEMENT: This paragraph shall provide stepbystep procedures for accomplishing the installation. References may be made to other documents, such as operator manuals. Safety precautions, marked by WARNING or CAUTION, shall be included where applicable. The procedures shall include the following, as applicable:Installing the softwareChecking out the software once installedInitializing databases and other software with sitespecific dataConversion from the current system, possibly involving running in para...
RATIONALE: Converted from SIP.html heading.

[REQUIREMENT]
UID: REQ-302
STATUS: Draft
TITLE: 4.x.6 Data update procedures.
STATEMENT: This paragraph shall present the data update procedures to be followed during the installation period. When the data update procedures are the same as normal updating or processing procedures, reference may be made to other documents, such as operator manuals.
RATIONALE: Converted from SIP.html heading.

[REQUIREMENT]
UID: REQ-303
STATUS: Draft
TITLE: 5. Sitespecific information for software users.
STATEMENT: This section shall provide installation planning pertinent to users of the software. When more than one type of user is involved, for example, users at different positions, performing different functions, or in different organizations, a separate section (Sections 5 through n) may be written for each type of user and the section titles modified to reflect each user.
RATIONALE: Converted from SIP.html heading.

[REQUIREMENT]
UID: REQ-304
STATUS: Draft
TITLE: 5.x (Site name).
STATEMENT: This paragraph shall identify a site or set of sites and shall be divided into the following subparagraphs to discuss those sites. Multiple sites may be discussed together when the information for those sites is generally the same.
RATIONALE: Converted from SIP.html heading.

[REQUIREMENT]
UID: REQ-305
STATUS: Draft
TITLE: 5.x.1 Schedule.
STATEMENT: This paragraph shall present a schedule of tasks to be accomplished by the user during installation. It shall depict the tasks in chronological order including beginning and ending dates for each task and supporting narrative as necessary.
RATIONALE: Converted from SIP.html heading.

[REQUIREMENT]
UID: REQ-306
STATUS: Draft
TITLE: 5.x.2 Installation procedures.
STATEMENT: This paragraph shall provide stepbystep procedures for accomplishing the installation. Reference may be made to other documents, such as user manuals. Safety precautions, marked by WARNING or CAUTION, shall be included where applicable. The procedures shall include the following, as applicable:Performing the tasks under 4.x.5 if not performed by operations staffInitializing userspecific dataSetting up queries and other user inputsPerforming sample processingGenerating sample reportsConversion...
RATIONALE: Converted from SIP.html heading.

[REQUIREMENT]
UID: REQ-307
STATUS: Draft
TITLE: 5.x.3 Data update procedures.
STATEMENT: This paragraph shall be divided into subparagraphs to present the user's data update procedures to be followed during the installation period. When update procedures are the same as normal processing, reference may be made to other documents, such as user manuals, and to Section 4 of this document
RATIONALE: Converted from SIP.html heading.

[REQUIREMENT]
UID: REQ-308
STATUS: Draft
TITLE: 6. Notes.
STATEMENT: This section shall contain any general information that aids in understanding this document (e.g., background information, glossary, rationale). This section shall include an alphabetical listing of all acronyms, abbreviations, and their meanings as used in this document and a list of terms and definitions needed to understand this document. If section 5 has been expanded into section(s) 6,...n, this section shall be numbered as the next section following section n.
RATIONALE: Converted from SIP.html heading.

[REQUIREMENT]
UID: REQ-309
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from SIP.html heading.
