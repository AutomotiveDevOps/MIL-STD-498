[DOCUMENT]
TITLE: COM

[GRAMMAR]
ELEMENTS:
- TAG: REQUIREMENT
  FIELDS:
  - TITLE: UID
    TYPE: String
    REQUIRED: True
  - TITLE: STATUS
    TYPE: String
    REQUIRED: True
  - TITLE: TITLE
    TYPE: String
    REQUIRED: True
  - TITLE: STATEMENT
    TYPE: String
    REQUIRED: True
  - TITLE: RATIONALE
    TYPE: String
    REQUIRED: True

[REQUIREMENT]
UID: REQ-406
STATUS: Draft
TITLE: 1. Scope.
STATEMENT: This section shall be divided into the following paragraphs.
RATIONALE: Converted from COM.html heading.

[REQUIREMENT]
UID: REQ-407
STATUS: Draft
TITLE: 1.1 Identification.
STATEMENT: This paragraph shall contain the manufacturer's name, model number, and any other identifying information for the computer system to which this COM applies.
RATIONALE: Converted from COM.html heading.

[REQUIREMENT]
UID: REQ-408
STATUS: Draft
TITLE: 1.2 Computer system overview.
STATEMENT: This paragraph shall briefly state the purpose of the computer system to which this COM applies.
RATIONALE: Converted from COM.html heading.

[REQUIREMENT]
UID: REQ-409
STATUS: Draft
TITLE: 1.3 Document overview.
STATEMENT: This paragraph shall summarize the purpose and contents of this manual and shall describe any security or privacy considerations associated with its use.
RATIONALE: Converted from COM.html heading.

[REQUIREMENT]
UID: REQ-410
STATUS: Draft
TITLE: 2. Referenced documents.
STATEMENT: This section shall list the number, title, revision, and date of all documents referenced in this manual. This section shall also identify the source for all documents not available through normal Government stocking activities.
RATIONALE: Converted from COM.html heading.

[REQUIREMENT]
UID: REQ-411
STATUS: Draft
TITLE: 3. Computer system operation.
STATEMENT: This section shall be divided into the following paragraphs. Safety precautions, marked by WARNING or CAUTION, shall be included where applicable.
RATIONALE: Converted from COM.html heading.

[REQUIREMENT]
UID: REQ-412
STATUS: Draft
TITLE: 3.1 Computer system preparation and shutdown.
STATEMENT: This paragraph shall be divided into the following subparagraphs.
RATIONALE: Converted from COM.html heading.

[REQUIREMENT]
UID: REQ-413
STATUS: Draft
TITLE: 3.1.1 Power on and off.
STATEMENT: This paragraph shall contain the procedures necessary to power on and power off the computer system.
RATIONALE: Converted from COM.html heading.

[REQUIREMENT]
UID: REQ-414
STATUS: Draft
TITLE: 3.1.2 Initiation.
STATEMENT: This paragraph shall contain the procedures necessary to initiate operation of the computer system, including, as applicable, equipment setup, pre operation, bootstrapping, and commands typically used during computer system initiation.
RATIONALE: Converted from COM.html heading.

[REQUIREMENT]
UID: REQ-415
STATUS: Draft
TITLE: 3.1.3 Shutdown.
STATEMENT: This paragraph shall contain the procedures necessary to terminate computer system operation.
RATIONALE: Converted from COM.html heading.

[REQUIREMENT]
UID: REQ-416
STATUS: Draft
TITLE: 3.2 Operating procedures.
STATEMENT: This paragraph shall be divided into the following subparagraphs. If more than one mode of operation is available, instructions for each mode shall be provided.
RATIONALE: Converted from COM.html heading.

[REQUIREMENT]
UID: REQ-417
STATUS: Draft
TITLE: 3.2.1 Input and output procedures.
STATEMENT: This paragraph shall describe the input and output media (e.g., magnetic disk, tape) relevant to the computer system, state the procedures to read and write on these media, briefly describe the operating system control language, and list procedures for interactive messages and replies (e.g, terminals to use, passwords, keys).
RATIONALE: Converted from COM.html heading.

[REQUIREMENT]
UID: REQ-418
STATUS: Draft
TITLE: 3.2.2 Monitoring procedures.
STATEMENT: This paragraph shall contain the procedures to be followed for monitoring the computer system in operation. It shall describe available indicators, interpretation of those indicators, and routine and special monitoring procedures to be followed.
RATIONALE: Converted from COM.html heading.

[REQUIREMENT]
UID: REQ-419
STATUS: Draft
TITLE: 3.2.3 Off line procedures.
STATEMENT: This paragraph shall contain the procedures necessary to operate all relevant off line equipment of the computer system.
RATIONALE: Converted from COM.html heading.

[REQUIREMENT]
UID: REQ-420
STATUS: Draft
TITLE: 3.2.4 Other procedures.
STATEMENT: This paragraph shall contain any additional procedures to be followed by the operator (e.g., computer system alarms, computer system security or privacy considerations, switch over to a redundant computer system, or other measures to ensure continuity of operations in the event of emergencies).
RATIONALE: Converted from COM.html heading.

[REQUIREMENT]
UID: REQ-421
STATUS: Draft
TITLE: 3.3 Problemhandling procedures.
STATEMENT: This paragraph shall identify problems that may occur in any step of operation described in the preceding paragraphs in Section 3. It shall state the error messages or other indications accompanying those problems and shall describe the automatic and manual procedures to be followed for each occurrence, including, as applicable, evaluation techniques, conditions requiring computer system shutdown, procedures for online intervention or abort, steps to be taken to restart computer system operat...
RATIONALE: Converted from COM.html heading.

[REQUIREMENT]
UID: REQ-422
STATUS: Draft
TITLE: 4. Diagnostic features.
STATEMENT: This section shall be divided into the following paragraphs to describe diagnostics that may be performed to identify and troubleshoot malfunctions in the computer system.
RATIONALE: Converted from COM.html heading.

[REQUIREMENT]
UID: REQ-423
STATUS: Draft
TITLE: 4.1 Diagnostic features summary.
STATEMENT: This paragraph shall summarize the diagnostic features of the computer system, including error message syntax and hierarchy for fault isolation. This paragraph shall describe the purpose of each diagnostic feature.
RATIONALE: Converted from COM.html heading.

[REQUIREMENT]
UID: REQ-424
STATUS: Draft
TITLE: 4.2 Diagnostic procedures.
STATEMENT: This paragraph shall be divided into subparagraphs as needed to describe the diagnostic procedures to be followed for the computer system, including:Identification of hardware, software, or firmware necessary for executing each procedureStep by step instructions for executing each procedureDiagnostic messages and the corresponding required action
RATIONALE: Converted from COM.html heading.

[REQUIREMENT]
UID: REQ-425
STATUS: Draft
TITLE: 4.3 Diagnostic tools.
STATEMENT: This paragraph shall be divided into subparagraphs as needed to describe the diagnostics tools available for the computer system. These tools may be hardware, software, or firmware. This paragraph shall identify each tool by name and number and shall describe the tool and its application.
RATIONALE: Converted from COM.html heading.

[REQUIREMENT]
UID: REQ-426
STATUS: Draft
TITLE: 5. Notes.
STATEMENT: This section shall contain any general information that aids in understanding this document (e.g., background information, glossary, rationale). This section shall include an alphabetical listing of all acronyms, abbreviations, and their meanings as used in this document and a list of terms and definitions needed to understand this document.
RATIONALE: Converted from COM.html heading.

[REQUIREMENT]
UID: REQ-427
STATUS: Draft
TITLE: A. Appendixes.
STATEMENT: Appendixes may be used to provide information published separately for convenience in document maintenance (e.g., charts, classified data). As applicable, each appendix shall be referenced in the main body of the document where the data would normally have been provided. Appendixes may be bound as separate documents for ease in handling. Appendixes shall be lettered alphabetically (A, B, etc.).
RATIONALE: Converted from COM.html heading.
